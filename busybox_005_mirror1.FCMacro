# -*- coding: utf-8 -*-

# Macro Begin: /home/amcintosh/Documents/FreeCAD/Busybox/busybox_005_mirror.FCMacro +++++++++++++++++++++++++++++++++++++++++++++++++
Gui.activeDocument().hide('pd_joist_loadcell')
#
this_mirror = App.activeDocument().bd_standard.newObject("PartDesign::Mirrored","Mirrored001")
App.ActiveDocument.recompute()
this_mirror.Originals = [App.activeDocument().pd_joist_loadcell,]
this_mirror.MirrorPlane = (App.activeDocument().XY_Plane, [""])
App.ActiveDocument.recompute()
App.activeDocument().bd_standard.Tip = this_mirror
App.ActiveDocument.recompute()
this_mirror.MirrorPlane = (App.ActiveDocument.pd_joist_loadcell, ["Face36"])
this_mirror.Originals = [App.ActiveDocument.pd_joist_loadcell, App.ActiveDocument.pd_joist, \
    App.ActiveDocument.pd_joist_extend,App.ActiveDocument.pd_support, App.ActiveDocument.pd_standard_extend, \
    App.ActiveDocument.pd_standard, ]
App.ActiveDocument.recompute()
Gui.activeDocument().show("Mirrored001")
Gui.activeDocument().hide("pd_joist_loadcell")
# Macro End: /home/amcintosh/Documents/FreeCAD/Busybox/busybox_005_mirror.FCMacro +++++++++++++++++++++++++++++++++++++++++++++++++
