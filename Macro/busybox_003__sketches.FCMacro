# -*- coding: utf-8 -*-

# Macro Begin: $HOME/Documents/FreeCAD/Busybox/busybox_003_sketches.FCMacro +++++++++++++++++++++++++++++++++++++++++++++++++
# ------------------------------------------------
# -- Create a global sketch group
# -- used in the project
# ------------------------------------------------
import FreeCAD
import Spreadsheet
import PartDesign
import PartDesignGui
import Sketcher

group_sketches = App.ActiveDocument.addObject('App::DocumentObjectGroup', 'group_sketches')
#
# ---- sk_footer
#
FreeCAD.Console.PrintMessage("Starting busybox_003_sketches --- footer.\n")
this_sketch = group_sketches.newObject('Sketcher::SketchObject','sk_footer_000')
this_sketch.Placement = App.Placement(App.Vector(0, 0, 0), \
    App.Rotation(-0.707107,0.000000,0.000000,-0.707107))
this_sketch.setExpression('Placement.Base.z', \
  u'-(sp_global.elevation-sp_joist.height-sp_footer.height+sp_footer.notch_depth)')
this_sketch.addGeometry(Part.LineSegment(App.Vector(-3.175000,0.000000,0),App.Vector(-3.175000,3.175000,0)),False)
this_sketch.addConstraint(Sketcher.Constraint('Vertical',0)) 
this_sketch.addGeometry(Part.LineSegment(App.Vector(3.175000,6.350000,0),App.Vector(-34.925000,6.350000,0)),False)
this_sketch.addConstraint(Sketcher.Constraint('Horizontal',1)) 
this_sketch.addGeometry(Part.LineSegment(App.Vector(-38.100000,6.350000,0),App.Vector(-38.100000,-12.700000,0)),False)
this_sketch.addConstraint(Sketcher.Constraint('Vertical',2)) 
this_sketch.addGeometry(Part.LineSegment(App.Vector(-34.925000,-12.700000,0),App.Vector(3.175000,-12.700000,0)),False)
this_sketch.addConstraint(Sketcher.Constraint('Horizontal',3)) 
this_sketch.addGeometry(Part.LineSegment(App.Vector(6.350000,-12.700000,0),App.Vector(6.350000,6.350000,0)),False)
this_sketch.addConstraint(Sketcher.Constraint('Vertical',4)) 
this_sketch.addConstraint(Sketcher.Constraint('DistanceX',3,1,3,2,38.100000)) 
this_sketch.setExpression('Constraints[5]', u'sp_footer.width')
this_sketch.addConstraint(Sketcher.Constraint('DistanceY',4,1,4,2,19.050000)) 
this_sketch.setExpression('Constraints[6]', u'sp_footer.height')
this_sketch.toggleConstruction(0) 
this_sketch.addConstraint(Sketcher.Constraint('DistanceY',0,1,0,2,3.175000)) 
this_sketch.setExpression('Constraints[7]', u'sp_footer.notch_depth')
this_sketch.addConstraint(Sketcher.Constraint('Coincident', 3, 2, 4, 1)) 
this_sketch.addConstraint(Sketcher.Constraint('Coincident', 1, 1, 4, 2)) 
this_sketch.addConstraint(Sketcher.Constraint('Coincident', 1, 2, 2, 1)) 
this_sketch.addConstraint(Sketcher.Constraint('Coincident', 2, 2, 3, 1)) 
this_sketch.addConstraint(Sketcher.Constraint('Coincident', 0, 1, -1, 1)) 
this_sketch.addConstraint(Sketcher.Constraint('Coincident', 1, 1, 0, 2)) 
#
# ---- sk_dowel
#
FreeCAD.Console.PrintMessage("Starting busybox_003_sketches --- dowel.\n")
this_sketch = this_sketch = group_sketches.newObject('Sketcher::SketchObject','sk_dowel_000')
this_sketch.setExpression('Placement.Base.z', \
  u'-(sp_global.elevation-sp_joist.height-sp_footer.height+sp_footer.notch_depth)')
this_sketch.MapMode = 'FlatFace'
this_sketch.addGeometry(Part.Circle(App.Vector(-17.876772,8.016674,0),App.Vector(0,0,1),4.487258),False)
this_sketch.addConstraint(Sketcher.Constraint('DistanceX',0,3,-1,1,-17.876772)) 
this_sketch.setExpression('Constraints[0]', u'sp_standard.length / 2')
this_sketch.addConstraint(Sketcher.Constraint('DistanceY',-1,1,0,3,-8.016674)) 
this_sketch.setExpression('Constraints[1]', u'sp_standard.width / 2')
this_sketch.addConstraint(Sketcher.Constraint('Diameter',0,8.974516)) 
this_sketch.setDatum(2,App.Units.Quantity('4.749800 mm'))
#
# ---- sk_support
#
FreeCAD.Console.PrintMessage("Starting busybox_003_sketches --- support.\n")
this_sketch = this_sketch = group_sketches.newObject('Sketcher::SketchObject','sk_support_old')
this_sketch.Placement = App.Placement(App.Vector(0.000000,0.000000,0.000000),App.Rotation(-0.707107,0.000000,0.000000,-0.707107))
this_sketch.MapMode = "Deactivated"

this_sketch.addGeometry(Part.Point(App.Vector(-6.350000,6.350000,0)))
this_sketch.addConstraint(Sketcher.Constraint('DistanceY',-1,1,0,1,6.350000)) 
this_sketch.setExpression('Constraints[0]', u'sp_support.height / 6')
this_sketch.addConstraint(Sketcher.Constraint('DistanceX',0,1,-1,1,6.350000)) 
this_sketch.setExpression('Constraints[1]', u'sp_standard.length / 6')
#
this_sketch.addGeometry(Part.Point(App.Vector(31.750000,6.350000,0)))
this_sketch.addConstraint(Sketcher.Constraint('DistanceX',0,1,1,1,38.100000)) 
this_sketch.setExpression('Constraints[2]', u'sp_support.width')
this_sketch.addConstraint(Sketcher.Constraint('Horizontal',1,1,0,1)) 
this_sketch.addGeometry(Part.Point(App.Vector(-6.350000,-31.750000,0)))
this_sketch.addConstraint(Sketcher.Constraint('DistanceY',2,1,0,1,38.100000)) 
this_sketch.setExpression('Constraints[4]', u'sp_support.height')
this_sketch.addConstraint(Sketcher.Constraint('Vertical',0,1,2,1)) 
this_sketch.setExpression('Constraints[1]', u'sp_standard.length / 4')
this_sketch.setExpression('Constraints[0]', u'sp_support.height / 4')
this_sketch.addGeometry(Part.Point(App.Vector(-9.525000,-22.225000,0)))
this_sketch.addGeometry(Part.Point(App.Vector(22.225000,9.525000,0)))
this_sketch.addGeometry(Part.LineSegment(App.Vector(-9.525000,-22.225000,0),App.Vector(22.225000,9.525000,0)),False)
this_sketch.addConstraint(Sketcher.Constraint('Coincident',5,1,3,1)) 
this_sketch.addConstraint(Sketcher.Constraint('Coincident',5,2,4,1)) 
this_sketch.addGeometry(Part.LineSegment(App.Vector(-9.525000,-28.575000,0),App.Vector(28.575000,9.525000,0)),False)
this_sketch.addConstraint(Sketcher.Constraint('Coincident',6,1,2,1)) 
this_sketch.addConstraint(Sketcher.Constraint('Coincident',6,2,1,1)) 
this_sketch.addConstraint(Sketcher.Constraint('Vertical',0,1,3,1)) 
#this_sketch.addConstraint(Sketcher.Constraint('Vertical',0,1,2,1)) 
this_sketch.addConstraint(Sketcher.Constraint('Horizontal',0,1,4,1)) 
#this_sketch.addConstraint(Sketcher.Constraint('Horizontal',0,1,1,1)) 
this_sketch.addGeometry(Part.Point(App.Vector(0.000000,-12.700000,0)))
this_sketch.addConstraint(Sketcher.Constraint('PointOnObject',7,1,5)) 
this_sketch.addGeometry(Part.LineSegment(App.Vector(0.000000,-12.700000,0),App.Vector(-9.525000,-12.700000,0)),False)
this_sketch.addConstraint(Sketcher.Constraint('Coincident',8,1,7,1)) 
this_sketch.addConstraint(Sketcher.Constraint('Horizontal',8)) 
this_sketch.addConstraint(Sketcher.Constraint('Vertical',0,1,8,2)) 
this_sketch.addGeometry(Part.LineSegment(App.Vector(0.000000,-12.700000,0),App.Vector(3.175000,-15.875000,0)),False)
this_sketch.addConstraint(Sketcher.Constraint('Coincident',9,1,7,1)) 
this_sketch.addConstraint(Sketcher.Constraint('PointOnObject',9,2,6)) 
this_sketch.addConstraint(Sketcher.Constraint('Perpendicular',6,9)) 
this_sketch.addConstraint(Sketcher.Constraint('Perpendicular',5,9)) 
this_sketch.addConstraint(Sketcher.Constraint('Vertical',-1,1,7,1)) 
this_sketch.addConstraint(Sketcher.Constraint('Distance',7,1,9,2,4.490128)) 
#this_sketch.setDatum(21,App.Units.Quantity('4.495800 mm'))
this_sketch.toggleConstruction(9) 
this_sketch.toggleConstruction(5) 
this_sketch.toggleConstruction(6) 
this_sketch.toggleConstruction(8) 
#
this_sketch.addGeometry(Part.LineSegment(App.Vector(0.000000,-12.700000,0),App.Vector(-9.525000,-15.875000,0)),False)
this_sketch.addConstraint(Sketcher.Constraint('Coincident',10,1,7,1)) 
this_sketch.addConstraint(Sketcher.Constraint('Vertical',0,1,10,2)) 
this_sketch.addConstraint(Sketcher.Constraint('Angle',8,1,10,1,0.321751)) 
this_sketch.setDatum(24,App.Units.Quantity('18.435000 deg'))
this_sketch.addGeometry(Part.LineSegment(App.Vector(0.000000,9.525000,0),App.Vector(-9.525000,6.350000,0)),False)
this_sketch.addConstraint(Sketcher.Constraint('PointOnObject',11,1,-2)) 
this_sketch.addConstraint(Sketcher.Constraint('Parallel',11,10)) 
this_sketch.addGeometry(Part.LineSegment(App.Vector(-9.525000,6.350000,0),App.Vector(-9.525000,-15.875000,0)),False)
this_sketch.addConstraint(Sketcher.Constraint('Coincident',12,1,11,2)) 
this_sketch.addConstraint(Sketcher.Constraint('Coincident',12,2,10,2)) 
this_sketch.addConstraint(Sketcher.Constraint('Vertical',12)) 
this_sketch.addConstraint(Sketcher.Constraint('Horizontal',0,1,11,1)) 
this_sketch.addGeometry(Part.Point(App.Vector(12.700000,9.525000,0)))
this_sketch.addGeometry(Part.LineSegment(App.Vector(12.700000,9.525000,0),App.Vector(19.050000,6.350000,0)),False)
this_sketch.addConstraint(Sketcher.Constraint('Coincident',14,1,13,1)) 
this_sketch.addConstraint(Sketcher.Constraint('PointOnObject',14,2,5)) 
this_sketch.addConstraint(Sketcher.Constraint('Angle',14,2,5,2,1.249046)) 
this_sketch.setDatum(33,App.Units.Quantity('71.565000 deg'))
this_sketch.addConstraint(Sketcher.Constraint('Horizontal',0,1,13,1)) 
this_sketch.setExpression('Constraints[0]', u'sp_support.height / 12')
this_sketch.addConstraint(Sketcher.Constraint('Horizontal',-1,1,14,2)) 
#
this_sketch.addGeometry(Part.LineSegment(App.Vector(0.000000,-19.050000,0),App.Vector(19.050000,0.000000,0)),False)
this_sketch.addConstraint(Sketcher.Constraint('Coincident',15,1,7,1)) 
this_sketch.addConstraint(Sketcher.Constraint('Coincident',15,2,14,2)) 
this_sketch.addGeometry(Part.LineSegment(App.Vector(12.700000,3.175000,0),App.Vector(0.000000,3.175000,0)),False)
this_sketch.addConstraint(Sketcher.Constraint('Coincident',16,1,13,1)) 
this_sketch.addConstraint(Sketcher.Constraint('Coincident',16,2,11,1)) 

#
# ---- sk_joist
#
FreeCAD.Console.PrintMessage("Starting busybox_003_sketches --- joist.\n") 
this_sketch = group_sketches.newObject('Sketcher::SketchObject','sk_joist_000')
this_sketch.Placement = App.Placement(App.Vector(0.000000,0.000000,0.000000),App.Rotation(0.500000,0.500000,0.500000,0.500000))
this_sketch.MapMode = 'FlatFace'
this_sketch.addGeometry(Part.LineSegment(App.Vector(19.050000,0.000000,0),App.Vector(38.100000,0.000000,0)),False)
this_sketch.addConstraint(Sketcher.Constraint('PointOnObject',0,1,-1)) 
this_sketch.addConstraint(Sketcher.Constraint('PointOnObject',0,2,-1)) 
this_sketch.addGeometry(Part.LineSegment(App.Vector(38.100000,0.000000,0),App.Vector(38.100000,38.100000,0)),False)
this_sketch.addConstraint(Sketcher.Constraint('Coincident',1,1,0,2)) 
this_sketch.addConstraint(Sketcher.Constraint('Vertical',1)) 
this_sketch.addGeometry(Part.LineSegment(App.Vector(38.100000,38.100000,0),App.Vector(19.050000,38.100000,0)),False)
this_sketch.addConstraint(Sketcher.Constraint('Coincident',2,1,1,2)) 
this_sketch.addConstraint(Sketcher.Constraint('Horizontal',2)) 
this_sketch.addGeometry(Part.LineSegment(App.Vector(19.050000,38.100000,0),App.Vector(19.050000,0.000000,0)),False)
this_sketch.addConstraint(Sketcher.Constraint('Coincident',3,1,2,2)) 
this_sketch.addConstraint(Sketcher.Constraint('Coincident',3,2,0,1)) 
this_sketch.addConstraint(Sketcher.Constraint('Vertical',3)) 
this_sketch.addConstraint(Sketcher.Constraint('DistanceX',-1,1,0,1,19.050000)) 
this_sketch.setExpression('Constraints[9]', u'sp_standard.width')
this_sketch.addConstraint(Sketcher.Constraint('DistanceX',0,1,0,2,19.050000)) 
this_sketch.setExpression('Constraints[10]', u'sp_joist.width')
this_sketch.addConstraint(Sketcher.Constraint('DistanceY',0,2,1,2,38.100000)) 
this_sketch.setExpression('Constraints[11]', u'sp_joist.height')
#this_sketch.setExpression('Placement.Base.y', u'sp_standard.width')
this_sketch.recompute()
#
# ---- sk_standardF
#
FreeCAD.Console.PrintMessage("Starting busybox_003_sketches --- standardF.\n") 
this_sketch = group_sketches.newObject('Sketcher::SketchObject','sk_standardF_000')
this_sketch.MapMode = 'FlatFace'
this_sketch.addGeometry(Part.LineSegment(App.Vector(-44.450000,47.625000,0),App.Vector(-6.350000,47.625000,0)),False)
this_sketch.addConstraint(Sketcher.Constraint('Horizontal',0)) 
this_sketch.addGeometry(Part.LineSegment(App.Vector(-44.450000,6.350000,0),App.Vector(-6.350000,6.350000,0)),False)
this_sketch.addConstraint(Sketcher.Constraint('Horizontal',1)) 
this_sketch.addGeometry(Part.LineSegment(App.Vector(6.350000,3.175000,0),App.Vector(6.350000,22.225000,0)),False)
this_sketch.addConstraint(Sketcher.Constraint('Vertical',2)) 
this_sketch.addGeometry(Part.LineSegment(App.Vector(-60.325000,31.750000,0),App.Vector(-60.325000,12.700000,0)),False)
this_sketch.addConstraint(Sketcher.Constraint('Vertical',3)) 
this_sketch.addConstraint(Sketcher.Constraint('DistanceY',2,1,2,2,19.050000)) 
this_sketch.setExpression('Constraints[4]', u'sp_standard.width')
this_sketch.addConstraint(Sketcher.Constraint('DistanceX',1,1,1,2,38.100000)) 
this_sketch.addConstraint(Sketcher.Constraint('Coincident', 3, 1, 0, 1)) 
this_sketch.addConstraint(Sketcher.Constraint('Coincident', 1, 1, 3, 2)) 
this_sketch.addConstraint(Sketcher.Constraint('Coincident', 0, 2, 2, 2)) 
this_sketch.movePoint(0,0,App.Vector(2.002364,5.961937,0),1)
this_sketch.addConstraint(Sketcher.Constraint('Coincident',2,1,1,2)) 
this_sketch.addConstraint(Sketcher.Constraint('Coincident',1,2,-1,1)) 
this_sketch.setExpression('Constraints[5]', u'sp_standard.length')
Gui.activeDocument().resetEdit()
#
#  ----  sk_spacer_notch
#
FreeCAD.Console.PrintMessage("Starting busybox_003_sketches --- spacer_notch.\n") 
aux_sketch = App.activeDocument().group_sketches.newObject('Sketcher::SketchObject','sk_spacer_notch_000')
# Aubrey --- I want to make the z value parametric off of a spreadsheet
#Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
aux_sketch.setExpression('Placement.Base.z', u'sp_joist.height-sp_spacer.notch_depth')
aux_sketch.addGeometry(Part.LineSegment(App.Vector(0.695014,19.050000,0),App.Vector(19.050000,19.050000,0)),False)
aux_sketch.addConstraint(Sketcher.Constraint('PointOnObject',0,1,-2)) 
aux_sketch.addConstraint(Sketcher.Constraint('Horizontal',0)) 
aux_sketch.addGeometry(Part.LineSegment(App.Vector(19.050000,19.050000,0),App.Vector(19.050000,38.100000,0)),False)
aux_sketch.addConstraint(Sketcher.Constraint('Coincident',1,1,0,2)) 
aux_sketch.addConstraint(Sketcher.Constraint('Vertical',1)) 
aux_sketch.addGeometry(Part.LineSegment(App.Vector(19.050000,38.100000,0),App.Vector(0.000000,38.100000,0)),False)
aux_sketch.addConstraint(Sketcher.Constraint('Coincident',2,1,1,2)) 
aux_sketch.addConstraint(Sketcher.Constraint('Horizontal',2)) 
aux_sketch.addGeometry(Part.LineSegment(App.Vector(0.000000,38.100000,0),App.Vector(0.000000,19.050000,0)),False)
aux_sketch.addConstraint(Sketcher.Constraint('Coincident',3,1,2,2)) 
aux_sketch.addConstraint(Sketcher.Constraint('Coincident',3,2,0,1)) 
aux_sketch.addConstraint(Sketcher.Constraint('Vertical',3)) 
aux_sketch.addConstraint(Sketcher.Constraint('DistanceX',2,2,1,2,19.050000)) 
aux_sketch.setDatum(9,App.Units.Quantity('19.050000 mm'))
aux_sketch.addConstraint(Sketcher.Constraint('DistanceY',0,2,1,2,19.050000)) 
aux_sketch.setDatum(10,App.Units.Quantity('19.050000 mm'))
aux_sketch.addConstraint(Sketcher.Constraint('DistanceY',-1,1,0,1,19.050000)) 
aux_sketch.setDatum(11,App.Units.Quantity('19.050000 mm'))
aux_sketch.setExpression('Constraints[9]', u'sp_spacer.width')
aux_sketch.setExpression('Constraints[10]', u'sp_joist.width')
aux_sketch.setExpression('Constraints[11]', u'sp_standard.width')
#
#  ----  sk_spacer_body
#
FreeCAD.Console.PrintMessage("Starting busybox_003_sketches --- spacer_body.\n") 
this_sketch = App.activeDocument().group_sketches.newObject('Sketcher::SketchObject','sk_spacer_body_000')
this_sketch.Placement = App.Placement(App.Vector(0, 0, 0), \
    App.Rotation(-0.707107,0.000000,0.000000,-0.707107))
#this_sketch.setExpression('Placement.Base.x', u'sp_spacer.width')
#this_sketch.setExpression('Placement.Base.z', u'sp_joist.height-sp_spacer.height')
#
this_sketch.addGeometry(Part.LineSegment(App.Vector(19.050000,0.000000,0),App.Vector(38.100000,0.000000,0)),False)
#this_sketch.addConstraint(Sketcher.Constraint('Horizontal',0)) 
this_sketch.addGeometry(Part.LineSegment(App.Vector(38.100000,0.000000,0),App.Vector(38.100000,38.100000,0)),False)
this_sketch.addConstraint(Sketcher.Constraint('Coincident',1,1,0,2)) 
this_sketch.addConstraint(Sketcher.Constraint('Vertical',1)) 
this_sketch.addGeometry(Part.LineSegment(App.Vector(38.100000,38.100000,0),App.Vector(19.050000,38.100000,0)),False)
this_sketch.addConstraint(Sketcher.Constraint('Coincident',2,1,1,2)) 
this_sketch.addConstraint(Sketcher.Constraint('Horizontal',2)) 
this_sketch.addGeometry(Part.LineSegment(App.Vector(19.050000,38.100000,0),App.Vector(19.050000,0.000000,0)),False)
this_sketch.addConstraint(Sketcher.Constraint('Coincident',3,1,2,2)) 
this_sketch.addConstraint(Sketcher.Constraint('Coincident',3,2,0,1)) 
this_sketch.addConstraint(Sketcher.Constraint('Vertical',3)) 
this_sketch.addConstraint(Sketcher.Constraint('DistanceY',0,2,1,2,38.100000)) 
this_sketch.setExpression('Constraints[7]', u'sp_spacer.height')
this_sketch.addConstraint(Sketcher.Constraint('Horizontal',0)) 
this_sketch.addConstraint(Sketcher.Constraint('DistanceX',0,1,0,2,19.050000)) 
this_sketch.setExpression('Constraints[9]', u'sp_spacer.width')
this_sketch.addConstraint(Sketcher.Constraint('DistanceY',-1,1,2,2,26.715581)) 
this_sketch.setExpression('Constraints[10]', u'sp_joist.height')
this_sketch.addConstraint(Sketcher.Constraint('PointOnObject',2,2,-2)) 
#
Gui.activeDocument().resetEdit()
Gui.activeDocument().activeView().viewIsometric()
Gui.SendMsgToActiveView("ViewFit")
# Macro End: $HOME/Documents/FreeCAD/Busybox/busybox_003_sketches.FCMacro +++++++++++++++++++++++++++++++++++++++++++++++++
