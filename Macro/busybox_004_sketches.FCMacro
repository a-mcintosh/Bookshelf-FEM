# -*- coding: utf-8 -*-

# Macro Begin: /home/amcintosh/Documents/FreeCAD/Busybox/Macro/aa_temp8.FCMacro +++++++++++++++++++++++++++++++++++++++++++++++++
import FreeCAD
import Sketcher

App.activeDocument().addObject('Sketcher::SketchObject','sk_support_000')
ActiveSketch = App.ActiveDocument.getObject('sk_support_000')
ActiveSketch.Placement = App.Placement(App.Vector(0.000000,0.000000,0.000000),App.Rotation(-0.707107,0.000000,0.000000,-0.707107))
ActiveSketch.MapMode = "Deactivated"
ActiveSketch.addGeometry(Part.Point(App.Vector(19.050000,0.836061,0)))
ActiveSketch.addGeometry(Part.Point(App.Vector(20.637500,2.427051,0)))
ActiveSketch.addGeometry(Part.Point(App.Vector(19.050000,3.175000,0)))
ActiveSketch.addGeometry(Part.Point(App.Vector(0.327038,3.175000,0)))
ActiveSketch.addGeometry(Part.Point(App.Vector(-0.335875,3.175000,0)))
ActiveSketch.addGeometry(Part.Point(App.Vector(0.327038,0.803086,0)))
ActiveSketch.addGeometry(Part.Point(App.Vector(-7.937500,0.438483,0)))
ActiveSketch.addGeometry(Part.Point(App.Vector(-9.525000,-1.587500,0)))
ActiveSketch.addGeometry(Part.Point(App.Vector(-7.163873,-1.587500,0)))
ActiveSketch.addGeometry(Part.Point(App.Vector(-7.229270,-23.185394,0)))
ActiveSketch.addGeometry(Part.Point(App.Vector(-9.525000,-23.085958,0)))
ActiveSketch.addGeometry(Part.Point(App.Vector(-6.350000,-25.400000,0)))
ActiveSketch.addGeometry(Part.Point(App.Vector(0.000000,-23.218540,0)))
ActiveSketch.addGeometry(Part.Point(App.Vector(-9.525000,-34.925000,0)))
ActiveSketch.addGeometry(Part.Point(App.Vector(1.222692,-24.463570,0)))
ActiveSketch.addGeometry(Part.Point(App.Vector(28.575000,3.175000,0)))
ActiveSketch.addGeometry(Part.Point(App.Vector(23.209347,0.000000,0)))
ActiveSketch.addGeometry(Part.Point(App.Vector(20.450228,3.252028,0)))
ActiveSketch.addGeometry(Part.Point(App.Vector(-0.139372,3.334008,0)))
ActiveSketch.addGeometry(Part.Point(App.Vector(-9.709600,0.244311,0)))
ActiveSketch.addGeometry(Part.Point(App.Vector(-8.980093,-26.003218,0)))
ActiveSketch.addGeometry(Part.Point(App.Vector(-9.202501,3.575147,0)))
ActiveSketch.addGeometry(Part.Point(App.Vector(-0.8,-0.8,0)))
#
# Macro End: /home/amcintosh/Documents/FreeCAD/Busybox/Macro/aa_temp8.FCMacro +++++++++++++++++++++++++++++++++++++++++++++++++
# -*- coding: utf-8 -*-

# Macro Begin: /home/amcintosh/Documents/FreeCAD/Busybox/Macro/aa_temp_02.FCMacro +++++++++++++++++++++++++++++++++++++++++++++++++
import FreeCAD
import Sketcher

ActiveSketch = App.ActiveDocument.getObject('sk_support_000')
ActiveSketch.addConstraint(Sketcher.Constraint('Horizontal',15,1,21,1)) 
ActiveSketch.addConstraint(Sketcher.Constraint('DistanceX',21,1,15,1,37.777501)) 
ActiveSketch.setExpression('Constraints[1]', u'sp_support.width')
ActiveSketch.addConstraint(Sketcher.Constraint('Vertical',21,1,13,1)) 
ActiveSketch.addConstraint(Sketcher.Constraint('DistanceY',13,1,21,1,38.100000)) 
ActiveSketch.setExpression('Constraints[3]', u'sp_support.height')
# Macro End: /home/amcintosh/Documents/FreeCAD/Busybox/Macro/aa_temp_02.FCMacro +++++++++++++++++++++++++++++++++++++++++++++++++
# -*- coding: utf-8 -*-

# Macro Begin: /home/amcintosh/Documents/FreeCAD/Busybox/Macro/aa_temp_03.FCMacro +++++++++++++++++++++++++++++++++++++++++++++++++
import FreeCAD
import Sketcher

ActiveSketch = App.ActiveDocument.getObject('sk_support_000')
ActiveSketch.addGeometry(Part.LineSegment(App.Vector(-9.525000,-34.925000,0),App.Vector(1.222692,-24.463573,0)),True)
ActiveSketch.addGeometry(Part.LineSegment(App.Vector(1.222692,-24.463573,0),App.Vector(28.826788,3.175000,0)),True)
ActiveSketch.addConstraint(Sketcher.Constraint('Coincident',23,1,13,1)) 
ActiveSketch.addGeometry(Part.LineSegment(App.Vector(0.000000,-23.218542,0),App.Vector(1.222692,-24.463573,0)),True)
ActiveSketch.addConstraint(Sketcher.Constraint('Vertical',22,1,12,1)) 
ActiveSketch.addConstraint(Sketcher.Constraint('Coincident',12,1,25,1)) 
ActiveSketch.addConstraint(Sketcher.Constraint('Perpendicular',23,25)) 
ActiveSketch.addConstraint(Sketcher.Constraint('Perpendicular',24,25)) 
ActiveSketch.addConstraint(Sketcher.Constraint('Coincident',14,1,23,2)) 
ActiveSketch.addConstraint(Sketcher.Constraint('Coincident',14,1,25,2)) 
ActiveSketch.addConstraint(Sketcher.Constraint('Coincident',14,1,24,1)) 
ActiveSketch.addConstraint(Sketcher.Constraint('Distance',25,2.272879)) 
ActiveSketch.setExpression('Constraints[12]', u'sp_support.blade_cut / 2')
# Macro End: /home/amcintosh/Documents/FreeCAD/Busybox/Macro/aa_temp_03.FCMacro +++++++++++++++++++++++++++++++++++++++++++++++++
# -*- coding: utf-8 -*-

# Macro Begin: /home/amcintosh/Documents/FreeCAD/Busybox/Macro/aa_temp_04.FCMacro +++++++++++++++++++++++++++++++++++++++++++++++++
import FreeCAD
import Sketcher

ActiveSketch = App.ActiveDocument.getObject('sk_support_000')
ActiveSketch.addGeometry(Part.LineSegment(App.Vector(19.049999,0.836061,0),App.Vector(20.637501,2.427051,0)),True)
ActiveSketch.addGeometry(Part.LineSegment(App.Vector(20.637501,2.427051,0),App.Vector(20.450228,3.252028,0)),True)
ActiveSketch.addGeometry(Part.LineSegment(App.Vector(20.419102,3.195044,0),App.Vector(19.049999,3.175000,0)),True)
ActiveSketch.addGeometry(Part.LineSegment(App.Vector(19.049999,3.175000,0),App.Vector(19.049999,0.836061,0)),True)
ActiveSketch.addGeometry(Part.ArcOfCircle(Part.Circle(App.Vector(19.049999,0.836061,0),App.Vector(0,0,1),2.247534),0.786496,1.570796),True)
ActiveSketch.addConstraint(Sketcher.Constraint('Coincident',30,2,2,1)) 
ActiveSketch.addConstraint(Sketcher.Constraint('Coincident',17,1,28,1)) 
ActiveSketch.addConstraint(Sketcher.Constraint('Coincident',2,1,28,2)) 
ActiveSketch.addConstraint(Sketcher.Constraint('Coincident',2,1,29,1)) 
ActiveSketch.addConstraint(Sketcher.Constraint('Perpendicular',27,26)) 
ActiveSketch.addConstraint(Sketcher.Constraint('Perpendicular',28,29)) 
ActiveSketch.addConstraint(Sketcher.Constraint('Coincident',26,2,1,1)) 
ActiveSketch.addConstraint(Sketcher.Constraint('Coincident',26,2,27,1)) 
ActiveSketch.addConstraint(Sketcher.Constraint('Coincident',30,1,1,1)) 
ActiveSketch.addConstraint(Sketcher.Constraint('Coincident',27,2,17,1)) 
ActiveSketch.addConstraint(Sketcher.Constraint('Coincident',26,1,29,2)) 
ActiveSketch.addConstraint(Sketcher.Constraint('Coincident',30,3,26,1)) 
ActiveSketch.addConstraint(Sketcher.Constraint('Coincident',26,1,0,1)) 
ActiveSketch.addConstraint(Sketcher.Constraint('Coincident',15,1,24,2)) 
ActiveSketch.addGeometry(Part.LineSegment(App.Vector(0.333119,0.799516,0),App.Vector(0.327038,3.175000,0)),True)
ActiveSketch.addConstraint(Sketcher.Constraint('Coincident',31,1,5,1)) 
ActiveSketch.addConstraint(Sketcher.Constraint('Coincident',31,2,3,1)) 
ActiveSketch.addConstraint(Sketcher.Constraint('Vertical',31)) 
ActiveSketch.addGeometry(Part.LineSegment(App.Vector(0.333119,3.175000,0),App.Vector(-0.139372,3.334008,0)),True)
ActiveSketch.addConstraint(Sketcher.Constraint('Coincident',32,1,3,1)) 
ActiveSketch.addConstraint(Sketcher.Constraint('Coincident',32,2,18,1)) 
ActiveSketch.addGeometry(Part.LineSegment(App.Vector(-0.139372,3.334008,0),App.Vector(-0.335875,3.175000,0)),True)
ActiveSketch.addConstraint(Sketcher.Constraint('Coincident',33,1,18,1)) 
ActiveSketch.addConstraint(Sketcher.Constraint('Coincident',33,2,4,1)) 
ActiveSketch.addGeometry(Part.LineSegment(App.Vector(-0.335875,3.175000,0),App.Vector(0.333119,0.799516,0)),True)
ActiveSketch.addConstraint(Sketcher.Constraint('Coincident',34,1,4,1)) 
ActiveSketch.addConstraint(Sketcher.Constraint('Coincident',34,2,5,1)) 
ActiveSketch.addConstraint(Sketcher.Constraint('Perpendicular',32,31)) 
ActiveSketch.addConstraint(Sketcher.Constraint('Perpendicular',34,33)) 
ActiveSketch.addGeometry(Part.ArcOfCircle(Part.Circle(App.Vector(0.325933,0.801433,0),App.Vector(0,0,1),2.429033),1.567838,1.846727),True)
ActiveSketch.addConstraint(Sketcher.Constraint('Coincident',35,3,5,1)) 
ActiveSketch.addConstraint(Sketcher.Constraint('Coincident',35,1,3,1)) 
ActiveSketch.addConstraint(Sketcher.Constraint('Coincident',35,2,4,1)) 
ActiveSketch.addGeometry(Part.LineSegment(App.Vector(-7.163873,-1.587500,0),App.Vector(-7.937500,0.438483,0)),True)
ActiveSketch.addConstraint(Sketcher.Constraint('Coincident',36,1,8,1)) 
ActiveSketch.addConstraint(Sketcher.Constraint('Coincident',36,2,6,1)) 
ActiveSketch.addGeometry(Part.LineSegment(App.Vector(-7.937500,0.438483,0),App.Vector(-9.709600,0.244311,0)),True)
ActiveSketch.addConstraint(Sketcher.Constraint('Coincident',37,1,6,1)) 
ActiveSketch.addConstraint(Sketcher.Constraint('Coincident',37,2,19,1)) 
ActiveSketch.addGeometry(Part.LineSegment(App.Vector(-9.709600,0.244311,0),App.Vector(-9.525000,-1.587500,0)),True)
ActiveSketch.addConstraint(Sketcher.Constraint('Coincident',38,1,19,1)) 
ActiveSketch.addConstraint(Sketcher.Constraint('Coincident',38,2,7,1)) 
ActiveSketch.addGeometry(Part.LineSegment(App.Vector(-9.525000,-1.587500,0),App.Vector(-7.163873,-1.587500,0)),True)
ActiveSketch.addConstraint(Sketcher.Constraint('Coincident',39,1,7,1)) 
ActiveSketch.addConstraint(Sketcher.Constraint('Coincident',39,2,8,1)) 
ActiveSketch.addConstraint(Sketcher.Constraint('Horizontal',39)) 
ActiveSketch.addConstraint(Sketcher.Constraint('Perpendicular',37,36)) 
ActiveSketch.addConstraint(Sketcher.Constraint('Perpendicular',39,38)) 
ActiveSketch.addGeometry(Part.ArcOfCircle(Part.Circle(App.Vector(-7.216743,-1.592726,0),App.Vector(0,0,1),2.394601),1.864784,3.141593),True)
ActiveSketch.addConstraint(Sketcher.Constraint('Coincident',40,3,8,1)) 
ActiveSketch.addConstraint(Sketcher.Constraint('Coincident',40,1,6,1)) 
ActiveSketch.addConstraint(Sketcher.Constraint('Coincident',40,2,7,1)) 
ActiveSketch.addGeometry(Part.LineSegment(App.Vector(-7.229270,-23.185396,0),App.Vector(-9.525000,-23.085960,0)),True)
ActiveSketch.addConstraint(Sketcher.Constraint('Coincident',41,1,9,1)) 
ActiveSketch.addConstraint(Sketcher.Constraint('Coincident',41,2,10,1)) 
ActiveSketch.addConstraint(Sketcher.Constraint('Horizontal',41)) 
ActiveSketch.addGeometry(Part.LineSegment(App.Vector(-9.525000,-23.185398,0),App.Vector(-9.025076,-25.934202,0)),True)
ActiveSketch.addConstraint(Sketcher.Constraint('Coincident',42,1,10,1)) 
ActiveSketch.addConstraint(Sketcher.Constraint('Coincident',42,2,20,1)) 
ActiveSketch.addGeometry(Part.LineSegment(App.Vector(-9.025076,-25.934206,0),App.Vector(-6.318978,-25.517879,0)),True)
ActiveSketch.addConstraint(Sketcher.Constraint('Coincident',43,1,20,1)) 
ActiveSketch.addConstraint(Sketcher.Constraint('Coincident',43,2,11,1)) 
ActiveSketch.addGeometry(Part.LineSegment(App.Vector(-6.318978,-25.559511,0),App.Vector(-7.229270,-23.185400,0)),True)
ActiveSketch.addConstraint(Sketcher.Constraint('Coincident',44,1,11,1)) 
ActiveSketch.addConstraint(Sketcher.Constraint('Coincident',44,2,9,1)) 
ActiveSketch.addConstraint(Sketcher.Constraint('Perpendicular',42,41)) 
ActiveSketch.addConstraint(Sketcher.Constraint('Perpendicular',44,43)) 
ActiveSketch.addGeometry(Part.ArcOfCircle(Part.Circle(App.Vector(-7.183267,-23.176697,0),App.Vector(0,0,1),1.896476),3.141593,4.909330),True)
ActiveSketch.addConstraint(Sketcher.Constraint('Coincident',45,3,9,1)) 
ActiveSketch.addConstraint(Sketcher.Constraint('Coincident',45,1,10,1)) 
ActiveSketch.addConstraint(Sketcher.Constraint('Coincident',45,2,11,1)) 
ActiveSketch.addConstraint(Sketcher.Constraint('Diameter',30,4.638936)) 
ActiveSketch.addConstraint(Sketcher.Constraint('Equal',30,35)) 
ActiveSketch.addConstraint(Sketcher.Constraint('Equal',30,40)) 
ActiveSketch.addConstraint(Sketcher.Constraint('Equal',30,45)) 
ActiveSketch.setDatum(69,App.Units.Quantity('4.622800 mm'))
# Macro End: /home/amcintosh/Documents/FreeCAD/Busybox/Macro/aa_temp_04.FCMacro +++++++++++++++++++++++++++++++++++++++++++++++++
# -*- coding: utf-8 -*-

# Macro Begin: /home/amcintosh/Documents/FreeCAD/Busybox/Macro/aa_temp_05.FCMacro +++++++++++++++++++++++++++++++++++++++++++++++++
import FreeCAD
import Sketcher

ActiveSketch = App.ActiveDocument.getObject('sk_support_000')
ActiveSketch.addGeometry(Part.LineSegment(App.Vector(19.121969,3.037695,0),App.Vector(0.318893,3.170556,0)),True)
ActiveSketch.addConstraint(Sketcher.Constraint('Coincident',46,1,2,1)) 
ActiveSketch.addConstraint(Sketcher.Constraint('Coincident',46,2,3,1)) 
ActiveSketch.addConstraint(Sketcher.Constraint('Horizontal',46)) 
ActiveSketch.addConstraint(Sketcher.Constraint('Perpendicular',46,29)) 
#ActiveSketch.addConstraint(Sketcher.Constraint('Perpendicular',31,46)) 
ActiveSketch.addGeometry(Part.LineSegment(App.Vector(-0.328835,3.123365,0),App.Vector(-7.903853,0.708426,0)),True)
ActiveSketch.addConstraint(Sketcher.Constraint('Coincident',47,1,4,1)) 
ActiveSketch.addConstraint(Sketcher.Constraint('Coincident',47,2,6,1)) 
ActiveSketch.addConstraint(Sketcher.Constraint('Perpendicular',47,34)) 
ActiveSketch.addConstraint(Sketcher.Constraint('Perpendicular',36,36)) 
ActiveSketch.addConstraint(Sketcher.Constraint('Perpendicular',36,47)) 
#ActiveSketch.addConstraint(Sketcher.Constraint('Perpendicular',36,47)) 
ActiveSketch.delConstraint(80)
ActiveSketch.addGeometry(Part.LineSegment(App.Vector(-9.567698,-1.495648,0),App.Vector(-9.387992,-23.421175,0)),True)
ActiveSketch.addConstraint(Sketcher.Constraint('Coincident',48,1,7,1)) 
ActiveSketch.addConstraint(Sketcher.Constraint('Coincident',48,2,10,1)) 
ActiveSketch.addConstraint(Sketcher.Constraint('Vertical',48)) 
#ActiveSketch.addConstraint(Sketcher.Constraint('Perpendicular',48,39)) 
#ActiveSketch.addConstraint(Sketcher.Constraint('Perpendicular',41,48)) 
ActiveSketch.addGeometry(Part.LineSegment(App.Vector(-6.876204,-25.764820,0),App.Vector(0.241498,-23.188477,0)),True)
ActiveSketch.addConstraint(Sketcher.Constraint('Coincident',49,1,11,1)) 
ActiveSketch.addConstraint(Sketcher.Constraint('Coincident',49,2,12,1)) 
ActiveSketch.addConstraint(Sketcher.Constraint('Perpendicular',49,44)) 
ActiveSketch.addConstraint(Sketcher.Constraint('Parallel',47,49)) 
ActiveSketch.addGeometry(Part.LineSegment(App.Vector(0.240140,-23.189465,0),App.Vector(23.209347,-0.000000,0)),True)
ActiveSketch.addConstraint(Sketcher.Constraint('Coincident',50,1,12,1)) 
ActiveSketch.addConstraint(Sketcher.Constraint('Coincident',50,2,16,1)) 
ActiveSketch.addGeometry(Part.LineSegment(App.Vector(23.209347,-0.000000,0),App.Vector(20.828791,2.430168,0)),True)
ActiveSketch.addConstraint(Sketcher.Constraint('Coincident',51,1,16,1)) 
ActiveSketch.addConstraint(Sketcher.Constraint('Coincident',51,2,1,1)) 
ActiveSketch.addConstraint(Sketcher.Constraint('Perpendicular',51,50)) 
ActiveSketch.addConstraint(Sketcher.Constraint('Perpendicular',26,51)) 
# Macro End: /home/amcintosh/Documents/FreeCAD/Busybox/Macro/aa_temp_05.FCMacro +++++++++++++++++++++++++++++++++++++++++++++++++
# -*- coding: utf-8 -*-

# Macro Begin: /home/amcintosh/Documents/FreeCAD/Busybox/Macro/aa_temp_06.FCMacro +++++++++++++++++++++++++++++++++++++++++++++++++
import FreeCAD
import Sketcher

ActiveSketch = App.ActiveDocument.getObject('sk_support_000')
ActiveSketch.addConstraint(Sketcher.Constraint('DistanceX',19,1,22,1,9.633817)) 
ActiveSketch.setExpression('Constraints[94]', u'sp_support.recess')
ActiveSketch.addConstraint(Sketcher.Constraint('DistanceY',22,1,18,1,4.014115)) 
ActiveSketch.setExpression('Constraints[95]', u'sp_support.key_height')
#ActiveSketch = App.ActiveDocument.getObject('Sketch001')
#tv = ActiveSketch.ViewObject.TempoVis
#if tv:
#  tv.restore()
#ActiveSketch.ViewObject.TempoVis = None
#del(tv)
#
#Gui.SendMsgToActiveView("ViewFit")
#ActiveSketch = App.ActiveDocument.getObject('Sketch001')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch001')
#if ActiveSketch.ViewObject.RestoreCamera:
#  ActiveSketch.ViewObject.TempoVis.saveCamera()
#
#Gui.SendMsgToActiveView("ViewFit")
ActiveSketch.addConstraint(Sketcher.Constraint('Horizontal',19,1,22,1)) 
ActiveSketch.addConstraint(Sketcher.Constraint('Horizontal',22,1,16,1)) 
#ActiveSketch.addConstraint(Sketcher.Constraint('Vertical',22,1,12,1)) #99
#Gui.SendMsgToActiveView("ViewFit")
ActiveSketch.movePoint(22,1,App.Vector(0.000000,0.000000,0),0)
ActiveSketch.movePoint(22,1,App.Vector(0.674556,0.405759,0),0)
ActiveSketch.movePoint(22,1,App.Vector(2.863921,1.603107,0),0)
ActiveSketch.movePoint(22,1,App.Vector(3.638549,1.965331,0),0)
ActiveSketch.addConstraint(Sketcher.Constraint('Perpendicular',50,25)) 
ActiveSketch.movePoint(22,1,App.Vector(2.640802,-2.979046,0),0)
ActiveSketch.movePoint(21,1,App.Vector(-7.112441,2.398910,0),0)
ActiveSketch.movePoint(21,1,App.Vector(-4.943318,2.606479,0),0)
ActiveSketch.addConstraint(Sketcher.Constraint('Vertical',21,1,19,1)) 
ActiveSketch.addConstraint(Sketcher.Constraint('Horizontal',18,1,21,1)) 
#Gui.SendMsgToActiveView("Save")
#App.getDocument("BusyBox_ver_1_1_3").save()
ActiveSketch.movePoint(48,0,App.Vector(-1.093822,-4.192989,0),1)
ActiveSketch.movePoint(48,0,App.Vector(-0.182304,1.093821,0),1)
ActiveSketch.movePoint(49,0,App.Vector(-1.093822,-1.002672,0),1)
ActiveSketch.movePoint(23,0,App.Vector(0.182303,0.000000,0),1)
ActiveSketch.movePoint(24,0,App.Vector(0.455762,-1.184975,0),1)
ActiveSketch.movePoint(50,0,App.Vector(-0.455759,-1.731886,0),1)
ActiveSketch.movePoint(46,0,App.Vector(0.091153,-0.182303,0),1)
ActiveSketch.movePoint(46,0,App.Vector(-2.096495,1.367280,0),1)
ActiveSketch.movePoint(15,1,App.Vector(27.555843,-4.776453,0),0)
ActiveSketch.movePoint(16,1,App.Vector(22.451336,-6.599492,0),0)
ActiveSketch.movePoint(14,1,App.Vector(5.543345,-28.599852,0),0)
ActiveSketch.movePoint(22,1,App.Vector(5.773998,-5.505811,0),0)
#ActiveSketch.addConstraint(Sketcher.Constraint('Vertical',22,1,12,1)) 
ActiveSketch.movePoint(14,1,App.Vector(8.339738,-36.616718,0),0)
ActiveSketch.movePoint(14,1,App.Vector(5.787479,-40.353947,0),0)
ActiveSketch.movePoint(22,1,App.Vector(4.335227,-18.036386,0),0)
ActiveSketch.movePoint(22,1,App.Vector(2.945421,-21.261719,0),0)
ActiveSketch.movePoint(22,1,App.Vector(6.159522,-21.689350,0),0)
ActiveSketch.addConstraint(Sketcher.Constraint('Vertical',18,1,22,1)) 
ActiveSketch.toggleConstruction(51) 
ActiveSketch.toggleConstruction(30) 
ActiveSketch.toggleConstruction(46) 
ActiveSketch.toggleConstruction(35) 
ActiveSketch.toggleConstruction(47) 
ActiveSketch.toggleConstruction(40) 
ActiveSketch.toggleConstruction(48) 
ActiveSketch.toggleConstruction(45) 
ActiveSketch.toggleConstruction(49) 
ActiveSketch.toggleConstruction(50) 
# Macro End: /home/amcintosh/Documents/FreeCAD/Busybox/Macro/aa_temp_06.FCMacro +++++++++++++++++++++++++++++++++++++++++++++++++
# -*- coding: utf-8 -*-

# Macro Begin: /home/amcintosh/Documents/FreeCAD/Busybox/Macro/aa_temp_07.FCMacro +++++++++++++++++++++++++++++++++++++++++++++++++
import FreeCAD
import Sketcher

ActiveSketch = App.ActiveDocument.getObject('sk_support_000')
ActiveSketch.movePoint(13,1,App.Vector(-10.783943,-32.877792,0),0)
ActiveSketch.addConstraint(Sketcher.Constraint('Coincident',22,1,-1,1)) 
group_sketches = App.ActiveDocument.getObject('group_sketches')
group_sketches.Group += [ActiveSketch, ]
App.ActiveDocument.recompute()

# Macro End: /home/amcintosh/Documents/FreeCAD/Busybox/Macro/aa_temp_07.FCMacro +++++++++++++++++++++++++++++++++++++++++++++++++
