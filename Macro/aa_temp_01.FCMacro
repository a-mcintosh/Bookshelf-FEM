# -*- coding: utf-8 -*-

# Macro Begin: /home/amcintosh/Documents/FreeCAD/Busybox/Macro/aa_temp8.FCMacro +++++++++++++++++++++++++++++++++++++++++++++++++
import FreeCAD
import Sketcher

App.activeDocument().addObject('Sketcher::SketchObject','sk_support_000')
ActiveSketch = App.ActiveDocument.getObject('sk_support_000')
ActiveSketch.Placement = App.Placement(App.Vector(0.000000,0.000000,0.000000),App.Rotation(-0.707107,0.000000,0.000000,-0.707107))
ActiveSketch.MapMode = "Deactivated"
ActiveSketch.addGeometry(Part.Point(App.Vector(19.050000,0.836061,0)))
ActiveSketch.addGeometry(Part.Point(App.Vector(20.637500,2.427051,0)))
ActiveSketch.addGeometry(Part.Point(App.Vector(19.050000,3.175000,0)))
ActiveSketch.addGeometry(Part.Point(App.Vector(0.327038,3.175000,0)))
ActiveSketch.addGeometry(Part.Point(App.Vector(-0.335875,3.175000,0)))
ActiveSketch.addGeometry(Part.Point(App.Vector(0.327038,0.803086,0)))
ActiveSketch.addGeometry(Part.Point(App.Vector(-7.937500,0.438483,0)))
ActiveSketch.addGeometry(Part.Point(App.Vector(-9.525000,-1.587500,0)))
ActiveSketch.addGeometry(Part.Point(App.Vector(-7.163873,-1.587500,0)))
ActiveSketch.addGeometry(Part.Point(App.Vector(-7.229270,-23.185394,0)))
ActiveSketch.addGeometry(Part.Point(App.Vector(-9.525000,-23.085958,0)))
ActiveSketch.addGeometry(Part.Point(App.Vector(-6.350000,-25.400000,0)))
ActiveSketch.addGeometry(Part.Point(App.Vector(0.000000,-23.218540,0)))
ActiveSketch.addGeometry(Part.Point(App.Vector(-9.525000,-34.925000,0)))
ActiveSketch.addGeometry(Part.Point(App.Vector(1.222692,-24.463570,0)))
ActiveSketch.addGeometry(Part.Point(App.Vector(28.575000,3.175000,0)))
ActiveSketch.addGeometry(Part.Point(App.Vector(23.209347,0.000000,0)))
ActiveSketch.addGeometry(Part.Point(App.Vector(20.450228,3.252028,0)))
ActiveSketch.addGeometry(Part.Point(App.Vector(-0.139372,3.334008,0)))
ActiveSketch.addGeometry(Part.Point(App.Vector(-9.709600,0.244311,0)))
ActiveSketch.addGeometry(Part.Point(App.Vector(-8.980093,-26.003218,0)))
ActiveSketch.addGeometry(Part.Point(App.Vector(-9.202501,3.575147,0)))
ActiveSketch.addGeometry(Part.Point(App.Vector(-0.8,-0.8,0)))
#
# Macro End: /home/amcintosh/Documents/FreeCAD/Busybox/Macro/aa_temp8.FCMacro +++++++++++++++++++++++++++++++++++++++++++++++++
