# -*- coding: utf-8 -*-

# Macro Begin: /home/amcintosh/Documents/FreeCAD/Busybox/Macro/aa_temp_03.FCMacro +++++++++++++++++++++++++++++++++++++++++++++++++
import FreeCAD
import Sketcher

ActiveSketch.addGeometry(Part.LineSegment(App.Vector(-9.525000,-34.925000,0),App.Vector(1.222692,-24.463573,0)),True)
ActiveSketch.addGeometry(Part.LineSegment(App.Vector(1.222692,-24.463573,0),App.Vector(28.826788,3.175000,0)),True)
ActiveSketch.addConstraint(Sketcher.Constraint('Coincident',23,1,13,1)) 
ActiveSketch.addGeometry(Part.LineSegment(App.Vector(0.000000,-23.218542,0),App.Vector(1.222692,-24.463573,0)),True)
ActiveSketch.addConstraint(Sketcher.Constraint('Vertical',22,1,12,1)) 
ActiveSketch.addConstraint(Sketcher.Constraint('Coincident',12,1,25,1)) 
ActiveSketch.addConstraint(Sketcher.Constraint('Perpendicular',23,25)) 
ActiveSketch.addConstraint(Sketcher.Constraint('Perpendicular',24,25)) 
ActiveSketch.addConstraint(Sketcher.Constraint('Coincident',14,1,23,2)) 
ActiveSketch.addConstraint(Sketcher.Constraint('Coincident',14,1,25,2)) 
ActiveSketch.addConstraint(Sketcher.Constraint('Coincident',14,1,24,1)) 
ActiveSketch.addConstraint(Sketcher.Constraint('Distance',25,2.272879)) 
ActiveSketch.setExpression('Constraints[12]', u'sp_support.blade_cut / 2')
App.ActiveDocument.recompute()
# Macro End: /home/amcintosh/Documents/FreeCAD/Busybox/Macro/aa_temp_03.FCMacro +++++++++++++++++++++++++++++++++++++++++++++++++
