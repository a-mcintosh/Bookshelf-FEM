#  --------------------------------------------------------
#  -- Copyright (c) 2020-06-24 by Aubrey McIntosh, PhD   --
#  -- Permission granted for use in educational settings --
#  -- and personal study with this notice left intact.   --
#  --------------------------------------------------------

# -*- coding: utf-8 -*-

# Macro Begin: $HOME/Documents/FreeCAD/Busybox/busybox_002_spreadsheets.FCMacro +++++++++++++++++++++++++++++++++++++++++++++++++
# ------------------------------------------------
# -- Create a spreadsheet group with parametric
# -- values used in the project
# ------------------------------------------------
import FreeCAD
import Spreadsheet
import PartDesign
import PartDesignGui
import Sketcher

FreeCAD.Console.PrintMessage("Starting busybox_002_spreadsheets.\n")
group_spreadsheets = App.ActiveDocument.addObject('App::DocumentObjectGroup', 'group_spreadsheets')
#
# ----
#
group_spreadsheets.newObject('Spreadsheet::Sheet','sp_global')
App.ActiveDocument.sp_global.setDisplayUnit('B2', 'in')
App.ActiveDocument.sp_global.setDisplayUnit('B3:B4', '')
App.ActiveDocument.sp_global.setDisplayUnit('B5', 'in')
#
App.ActiveDocument.sp_global.set('A2', 'first_shelf_elevation')
App.ActiveDocument.sp_global.set('B2', '5"')
App.ActiveDocument.sp_global.setAlias('B2', 'first_shelf_elevation')
#
App.ActiveDocument.sp_global.set('A3', 'shelf_nr')  #like stories of a building
App.ActiveDocument.sp_global.set('B3', '0')
App.ActiveDocument.sp_global.setAlias('B3', 'shelf_nr')
#
App.ActiveDocument.sp_global.set('A4', 'standard_count')
App.ActiveDocument.sp_global.set('B4', '6')
App.ActiveDocument.sp_global.setAlias('B4', 'standard_count')
#
App.ActiveDocument.sp_global.set('A5', 'small_tool_dia')
App.ActiveDocument.sp_global.set('B5', '0.125"')
App.ActiveDocument.sp_global.setAlias('B5', 'small_tool_dia')
#
App.ActiveDocument.sp_global.set('A6', 'wood_stock_thickness')
App.ActiveDocument.sp_global.set('B6', '19mm')
App.ActiveDocument.sp_global.setAlias('B6', 'wood_stock_thickness')
#
# ---- footer
#
group_spreadsheets.newObject('Spreadsheet::Sheet','sp_footer')
App.ActiveDocument.sp_footer.setDisplayUnit('B3:B8', 'in')
#
App.ActiveDocument.sp_footer.set('A3', 'hight')
App.ActiveDocument.sp_footer.set('B3', '0.75"')
App.ActiveDocument.sp_footer.setAlias('B3', 'height')
#
App.ActiveDocument.sp_footer.set('A4', 'width')
App.ActiveDocument.sp_footer.set('B4', '1.5"')
App.ActiveDocument.sp_footer.setAlias('B4', 'width')
#
App.ActiveDocument.sp_footer.set('A5', 'length')
App.ActiveDocument.sp_footer.set('B5', '20"')
App.ActiveDocument.sp_footer.setAlias('B5', 'length')
#
App.ActiveDocument.sp_footer.set('A6', 'notch depth')
App.ActiveDocument.sp_footer.set('B6', '0.1875"')
App.ActiveDocument.sp_footer.setAlias('B6', 'notch_depth')
#
App.ActiveDocument.sp_footer.setDisplayUnit('B8:B9', 'in')
App.ActiveDocument.sp_footer.set('A7', 'dowel length')
App.ActiveDocument.sp_footer.setAlias('B7', 'dowel_length')
App.ActiveDocument.sp_footer.set('B7', '0.5"')
#
App.ActiveDocument.sp_footer.set('A8', 'dowel dia')
App.ActiveDocument.sp_footer.setAlias('B8', 'dowel_dia')
App.ActiveDocument.sp_footer.set('B8', '=(0.125in+0.0625in)')
#
# --------  standard
#
group_spreadsheets.newObject('Spreadsheet::Sheet','sp_standard')
App.ActiveDocument.sp_standard.setDisplayUnit('B2:B6', 'in')
#
App.ActiveDocument.sp_standard.set('A2', 'length')
App.ActiveDocument.sp_standard.set('B2', '1.5"')
App.ActiveDocument.sp_standard.setAlias('B2', 'length')
#
App.ActiveDocument.sp_standard.set('A3', 'width')
App.ActiveDocument.sp_standard.set('B3', '0.75"')
App.ActiveDocument.sp_standard.setAlias('B3', 'width')
#
App.ActiveDocument.sp_standard.set('A4', 'height')
App.ActiveDocument.sp_standard.set('B4', '2252.66 mm')	#was 84".  Changed to make part symmetric, adjusted joist height.  Self modifies.
App.ActiveDocument.sp_standard.setAlias('B4', 'height')
#
App.ActiveDocument.sp_standard.set('A5', 'notch depth')
App.ActiveDocument.sp_standard.set('B5', '0.125"')
App.ActiveDocument.sp_standard.setAlias('B5', 'notch_depth')
#
App.ActiveDocument.sp_standard.set('A6', 'item height')
App.ActiveDocument.sp_standard.set('B6', '13.5"')
App.ActiveDocument.sp_standard.setAlias('B6', 'item_height')
#
App.ActiveDocument.sp_standard.set('A7', 'shelf_count')
App.ActiveDocument.sp_standard.set('B7', '7')
App.ActiveDocument.sp_standard.setAlias('B7', 'shelf_count')
#
App.ActiveDocument.recompute()
#
# --------  support
#
group_spreadsheets.newObject('Spreadsheet::Sheet','sp_support')
App.ActiveDocument.sp_support.setDisplayUnit('B2:B9', 'in')
#
App.ActiveDocument.sp_support.set('A2', 'length')
App.ActiveDocument.sp_support.set('B2', '20"')
App.ActiveDocument.sp_support.setAlias('B2', 'length')
#
App.ActiveDocument.sp_support.set('A3', 'width')
App.ActiveDocument.sp_support.set('B3', '1.5"')
App.ActiveDocument.sp_support.setAlias('B3', 'width')
#
App.ActiveDocument.sp_support.set('A4', 'height')
App.ActiveDocument.sp_support.set('B4', '1.00"')
App.ActiveDocument.sp_support.setAlias('B4', 'height')
#
App.ActiveDocument.sp_support.set('A5', 'key_height')
App.ActiveDocument.sp_support.set('B5', '0.125"')
App.ActiveDocument.sp_support.setAlias('B5', 'key_height')
#
App.ActiveDocument.sp_support.set('A6', 'blade_cut')
App.ActiveDocument.sp_support.set('B6', '0.125"')
App.ActiveDocument.sp_support.setAlias('B6', 'blade_cut')
#
App.ActiveDocument.sp_support.set('A7', 'dia_router')
App.ActiveDocument.sp_support.set('B7', '0.1825"')
App.ActiveDocument.sp_support.setAlias('B7', 'dia_router')
#
App.ActiveDocument.sp_support.set('A8', 'recess')
App.ActiveDocument.sp_support.set('B8', '0.375"')
App.ActiveDocument.sp_support.setAlias('B8', 'recess')
#
App.ActiveDocument.sp_support.set('A9', 'face_size')
App.ActiveDocument.sp_support.set('B9', '0.5"')
App.ActiveDocument.sp_support.setAlias('B9', 'face_size')
#
# --------  joist
#
group_spreadsheets.newObject('Spreadsheet::Sheet','sp_joist')
App.ActiveDocument.sp_joist.setDisplayUnit('B2:B5', 'in')
#
App.ActiveDocument.sp_joist.set('A2', 'length')
App.ActiveDocument.sp_joist.set('B2', '48"')
App.ActiveDocument.sp_joist.setAlias('B2', 'length')
#
App.ActiveDocument.sp_joist.set('A3', 'width')
App.ActiveDocument.sp_joist.set('B3', '0.75"')
App.ActiveDocument.sp_joist.setAlias('B3', 'width')
#
App.ActiveDocument.sp_joist.set('A4', 'height')
App.ActiveDocument.sp_joist.set('B4', '1.00"')
App.ActiveDocument.sp_joist.setAlias('B4', 'height')
#
App.ActiveDocument.sp_joist.set('A5', 'notch depth')
App.ActiveDocument.sp_joist.set('B5', '0.125"')
App.ActiveDocument.sp_joist.setAlias('B5', 'notch_depth')
#
App.ActiveDocument.sp_joist.set('A6', 'spacer count')
App.ActiveDocument.sp_joist.set('B6', '9')
App.ActiveDocument.sp_joist.setAlias('B6', 'spacer_count')
#
# --------  spacer
#
group_spreadsheets.newObject('Spreadsheet::Sheet','sp_spacer')
App.ActiveDocument.sp_spacer.setDisplayUnit('B2:B5', 'in')
#
App.ActiveDocument.sp_spacer.set('A2', 'length')
#App.ActiveDocument.sp_spacer.set('B2', '54"')
App.ActiveDocument.sp_spacer.setAlias('B2', 'length')
#
App.ActiveDocument.sp_spacer.set('A3', 'width')
App.ActiveDocument.sp_spacer.set('B3', '0.75"')
App.ActiveDocument.sp_spacer.setAlias('B3', 'width')
#
App.ActiveDocument.sp_spacer.set('A4', 'height')
App.ActiveDocument.sp_spacer.set('B4', '0.75"')
App.ActiveDocument.sp_spacer.setAlias('B4', 'height')
#
App.ActiveDocument.sp_spacer.set('A5', 'notch depth')
App.ActiveDocument.sp_spacer.set('B5', '0.125"')
App.ActiveDocument.sp_spacer.setAlias('B5', 'notch_depth')
#
App.ActiveDocument.sp_spacer.set('A6', 'spacer count')
App.ActiveDocument.sp_spacer.set('B6', '5')
App.ActiveDocument.sp_spacer.setAlias('B6', 'spacer_count')
#
# --------------------------------
#
# Macro End: $HOME/Documents/FreeCAD/Busybox/busybox_002_spreadsheets.FCMacro +++++++++++++++++++++++++++++++++++++++++++++++++
