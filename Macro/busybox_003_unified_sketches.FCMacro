#  --------------------------------------------------------
#  -- Copyright (c) 2020-06-24 by Aubrey McIntosh, PhD   --
#  -- Permission granted for use in educational settings --
#  -- and personal study with this notice left intact.   --
#  --------------------------------------------------------

# -*- coding: utf-8 -*-

# Macro Begin: $HOME/Documents/FreeCAD/Busybox/busybox_003_sketches.FCMacro +++++++++++++++++++++++++++++++++++++++++++++++++
# ------------------------------------------------
# -- Create a global sketch group
# -- used in the project
# ------------------------------------------------
import FreeCAD
import Spreadsheet
import PartDesign
import PartDesignGui
import Sketcher
import math

group_sketches = App.ActiveDocument.addObject('App::DocumentObjectGroup', 'group_sketches')
#
# ---- sk_footer
#
FreeCAD.Console.PrintMessage("Starting busybox_003_sketches --- footer.\n")
this_sketch = group_sketches.newObject('Sketcher::SketchObject','sk_footer_000')
this_sketch.Placement = App.Placement(App.Vector(0, 0, 0), \
    App.Rotation(-0.707107,0.000000,0.000000,-0.707107))
this_sketch.setExpression('Placement.Base.z', \
  u'-(sp_global.first_shelf_elevation-sp_joist.height-sp_footer.height+sp_footer.notch_depth)')
this_sketch.addGeometry(Part.LineSegment(App.Vector(-3.175000,0.000000,0),App.Vector(-3.175000,3.175000,0)),False)
this_sketch.addConstraint(Sketcher.Constraint('Vertical',0)) 
this_sketch.addGeometry(Part.LineSegment(App.Vector(3.175000,6.350000,0),App.Vector(-34.925000,6.350000,0)),False)
this_sketch.addConstraint(Sketcher.Constraint('Horizontal',1)) 
this_sketch.addGeometry(Part.LineSegment(App.Vector(-38.100000,6.350000,0),App.Vector(-38.100000,-12.700000,0)),False)
this_sketch.addConstraint(Sketcher.Constraint('Vertical',2)) 
this_sketch.addGeometry(Part.LineSegment(App.Vector(-34.925000,-12.700000,0),App.Vector(3.175000,-12.700000,0)),False)
this_sketch.addConstraint(Sketcher.Constraint('Horizontal',3)) 
this_sketch.addGeometry(Part.LineSegment(App.Vector(6.350000,-12.700000,0),App.Vector(6.350000,6.350000,0)),False)
this_sketch.addConstraint(Sketcher.Constraint('Vertical',4)) 
this_sketch.addConstraint(Sketcher.Constraint('DistanceX',3,1,3,2,38.100000)) 
this_sketch.setExpression('Constraints[5]', u'sp_footer.width')
this_sketch.addConstraint(Sketcher.Constraint('DistanceY',4,1,4,2,19.050000)) 
this_sketch.setExpression('Constraints[6]', u'sp_footer.height')
this_sketch.toggleConstruction(0) 
this_sketch.addConstraint(Sketcher.Constraint('DistanceY',0,1,0,2,3.175000)) 
this_sketch.setExpression('Constraints[7]', u'sp_footer.notch_depth')
this_sketch.addConstraint(Sketcher.Constraint('Coincident', 3, 2, 4, 1)) 
this_sketch.addConstraint(Sketcher.Constraint('Coincident', 1, 1, 4, 2)) 
this_sketch.addConstraint(Sketcher.Constraint('Coincident', 1, 2, 2, 1)) 
this_sketch.addConstraint(Sketcher.Constraint('Coincident', 2, 2, 3, 1)) 
this_sketch.addConstraint(Sketcher.Constraint('Coincident', 0, 1, -1, 1)) 
this_sketch.addConstraint(Sketcher.Constraint('Coincident', 1, 1, 0, 2)) 
#
# ---- sk_dowel
#
FreeCAD.Console.PrintMessage("Starting busybox_003_sketches --- dowel.\n")
this_sketch = this_sketch = group_sketches.newObject('Sketcher::SketchObject','sk_dowel_000')
#this_sketch.setExpression('Placement.Base.y', \
#  u'(sp_global.small_tool_dia)')
this_sketch.setExpression('Placement.Base.z', \
  u'-(sp_global.first_shelf_elevation-sp_joist.height-sp_footer.height+sp_footer.notch_depth)')
this_sketch.MapMode = 'FlatFace'
this_sketch.addGeometry(Part.Circle(App.Vector(-17.876772,8.016674,0),App.Vector(0,0,1),4.487258),False)
this_sketch.addConstraint(Sketcher.Constraint('DistanceX',0,3,-1,1,-17.876772)) 
this_sketch.setExpression('Constraints[0]', u'sp_standard.length / 2')
this_sketch.addConstraint(Sketcher.Constraint('DistanceY',-1,1,0,3,-8.016674)) 
this_sketch.setExpression('Constraints[1]', u'sp_standard.width / 2')
this_sketch.addConstraint(Sketcher.Constraint('Diameter',0,8.974516)) 
this_sketch.setDatum(2,App.Units.Quantity('4.749800 mm'))
#
this_sketch.addGeometry(Part.LineSegment(App.Vector(-16.66875,3.175000,0),App.Vector(-16.66875,15.875000,0)),True)
this_sketch.addGeometry(Part.LineSegment(App.Vector(-16.66875,15.875000,0),App.Vector(-22.225000,15.875000,0)),True)
this_sketch.addGeometry(Part.LineSegment(App.Vector(-21.43125,15.875000,0),App.Vector(-21.253139,3.175000,0)),True)
this_sketch.addGeometry(Part.LineSegment(App.Vector(-21.43125,3.175000,0),App.Vector(-18.130760,3.175000,0)),True)
#
this_sketch.addConstraint(Sketcher.Constraint('Vertical',1)) 
this_sketch.addConstraint(Sketcher.Constraint('DistanceY',-1,1,1,1,3.175000)) 
this_sketch.setExpression('Constraints[4]', u'sp_global.small_tool_dia')
this_sketch.addConstraint(Sketcher.Constraint('DistanceY',1,1,1,2,12.700000)) 
this_sketch.setExpression('Constraints[5]', u'sp_standard.width - 2 * sp_global.small_tool_dia')
this_sketch.addConstraint(Sketcher.Constraint('Coincident',2,1,1,2)) 
this_sketch.addConstraint(Sketcher.Constraint('Horizontal',2)) 
this_sketch.addConstraint(Sketcher.Constraint('DistanceX',2,2,2,1,4.7625)) 
this_sketch.setExpression('Constraints[8]', u'sp_global.small_tool_dia')
this_sketch.addConstraint(Sketcher.Constraint('Coincident',3,1,2,2)) 
this_sketch.addConstraint(Sketcher.Constraint('Vertical',3)) 
this_sketch.addConstraint(Sketcher.Constraint('Coincident',4,1,3,2)) 
this_sketch.addConstraint(Sketcher.Constraint('Coincident',4,2,1,1)) 
this_sketch.addConstraint(Sketcher.Constraint('Symmetric',3,2,1,2,0,3)) 
this_sketch.setExpression('Constraints[8]', u'sp_footer.dowel_dia')
this_sketch.toggleConstruction(2) 
this_sketch.toggleConstruction(3) 
this_sketch.toggleConstruction(4) 
this_sketch.toggleConstruction(1) 
this_sketch.toggleConstruction(0) 
#
#  ---- tenon_detail  --  footer - standard interface
#
this_sketch = App.activeDocument().group_sketches.newObject('Sketcher::SketchObject','sk_tenon_detail_000')
this_sketch.Placement = App.Placement(App.Vector(0, 0, 0), \
    App.Rotation(-0.707107,0.000000,0.000000,-0.707107))
this_sketch.setExpression('Placement.Base.y', \
  u'(sp_global.small_tool_dia)')
this_sketch.setExpression('Placement.Base.z', \
  u'-(sp_global.first_shelf_elevation-sp_joist.height-sp_footer.height+sp_footer.notch_depth)')


this_sketch.addGeometry(Part.LineSegment(App.Vector(-16.668749,4.7625,0),App.Vector(-17.9411,4.7625,0)),True)
this_sketch.addGeometry(Part.LineSegment(App.Vector(-16.668749,4.7625,0),App.Vector(-17.9411,3.4901,0)),True)
this_sketch.addGeometry(Part.LineSegment(App.Vector(-21.43125,4.7625,0),App.Vector(-21.43125,3.4901,0)),True)
this_sketch.addGeometry(Part.LineSegment(App.Vector(-21.43125,4.7625,0),App.Vector(-20.158882,4.7625,0)),True)
this_sketch.addGeometry(Part.ArcOfCircle(Part.Circle(App.Vector(-17.9411,3.4901,0),App.Vector(0,0,1),1.272366),0.000000,1.495460),True)
this_sketch.addGeometry(Part.ArcOfCircle(Part.Circle(App.Vector(-20.1588,3.4901,0),App.Vector(0,0,1),1.269112),1.557584,3.141595),True)
this_sketch.addGeometry(Part.LineSegment(App.Vector(-21.43125,3.4901,0),App.Vector(-20.158882,4.7625,0)),True)
this_sketch.addGeometry(Part.LineSegment(App.Vector(-17.9411,4.7625,0),App.Vector(-16.668749,3.4901,0)),True)
this_sketch.addGeometry(Part.Point(App.Vector(-19.050000,4.7625,0)))

this_sketch.addGeometry(Part.LineSegment(App.Vector(-21.417652,3.175000,0),App.Vector(-16.643349,3.175000,0)),True)
#
this_sketch.addGeometry(Part.LineSegment(App.Vector(-16.668750,4.762500,0),App.Vector(-16.668750,5.556250,0)),True)
this_sketch.addGeometry(Part.LineSegment(App.Vector(-16.668750,5.556250,0),App.Vector(-21.431250,5.556250,0)),True)
this_sketch.addGeometry(Part.LineSegment(App.Vector(-21.431250,5.556250,0),App.Vector(-21.431250,4.762500,0)),True)
this_sketch.addGeometry(Part.LineSegment(App.Vector(-19.843750,4.762500,0),App.Vector(-18.256250,4.762500,0)),True)
#
this_sketch.addGeometry(Part.LineSegment(App.Vector(-16.668750,0.000000,0),App.Vector(-16.668750,3.175000,0)),True)
this_sketch.addGeometry(Part.LineSegment(App.Vector(-21.431250,3.175000,0),App.Vector(-21.431250,0.000000,0)),True)
this_sketch.addGeometry(Part.LineSegment(App.Vector(-21.431250,0.000000,0),App.Vector(-16.668750,0.000000,0)),True)
#
this_sketch.addConstraint(Sketcher.Constraint('DistanceX',2,1,0,1,5.386060)) 
this_sketch.addConstraint(Sketcher.Constraint('Horizontal',0)) 
this_sketch.addConstraint(Sketcher.Constraint('Coincident',1,1,0,1)) 
this_sketch.addConstraint(Sketcher.Constraint('Vertical',2)) 
this_sketch.addConstraint(Sketcher.Constraint('Coincident',3,1,2,1)) 
#this_sketch.addConstraint(Sketcher.Constraint('Coincident',4,1,1,2)) 
this_sketch.addConstraint(Sketcher.Constraint('Coincident',4,2,0,2)) 
this_sketch.addConstraint(Sketcher.Constraint('Coincident',5,1,3,2)) 
this_sketch.addConstraint(Sketcher.Constraint('Coincident',5,2,2,2)) 
this_sketch.addConstraint(Sketcher.Constraint('Horizontal',3)) 
this_sketch.addConstraint(Sketcher.Constraint('Vertical',1)) 
this_sketch.addConstraint(Sketcher.Constraint('Tangent',4,1,1,2)) 
this_sketch.addConstraint(Sketcher.Constraint('Tangent',4,0)) 
this_sketch.addConstraint(Sketcher.Constraint('Tangent',3,5)) 
this_sketch.addConstraint(Sketcher.Constraint('Tangent',2,5)) 
this_sketch.addConstraint(Sketcher.Constraint('Diameter',4,2.544733)) 
this_sketch.addConstraint(Sketcher.Constraint('Equal',4,5)) 
this_sketch.addConstraint(Sketcher.Constraint('Horizontal',5,3,4,3)) 
this_sketch.addConstraint(Sketcher.Constraint('DistanceY',-1,1,0,1,5.457230)) 
this_sketch.addConstraint(Sketcher.Constraint('Coincident',6,1,2,2)) 
this_sketch.addConstraint(Sketcher.Constraint('Coincident',6,2,3,2)) 
this_sketch.addConstraint(Sketcher.Constraint('Coincident',7,1,0,2)) 
this_sketch.addConstraint(Sketcher.Constraint('Coincident',7,2,1,2)) 
this_sketch.addConstraint(Sketcher.Constraint('DistanceX',8,1,-1,1,19.050000)) 
this_sketch.addConstraint(Sketcher.Constraint('Symmetric',3,2,0,2,8,1)) 
#
this_sketch.addConstraint(Sketcher.Constraint('Coincident',9,1,0,1)) 
this_sketch.addConstraint(Sketcher.Constraint('Vertical',9)) 
this_sketch.addConstraint(Sketcher.Constraint('Coincident',10,1,9,2)) 
this_sketch.addConstraint(Sketcher.Constraint('Horizontal',10)) 
this_sketch.addConstraint(Sketcher.Constraint('Coincident',11,1,10,2)) 
this_sketch.addConstraint(Sketcher.Constraint('Coincident',11,2,2,1)) 
this_sketch.addConstraint(Sketcher.Constraint('Vertical',11)) 
this_sketch.addConstraint(Sketcher.Constraint('Coincident',12,1,3,2)) 
this_sketch.addConstraint(Sketcher.Constraint('Coincident',12,2,0,2)) 
this_sketch.addConstraint(Sketcher.Constraint('DistanceY',0,1,9,2,0.793750)) 
#
this_sketch.addConstraint(Sketcher.Constraint('Coincident',13,1,2,2)) 
this_sketch.addConstraint(Sketcher.Constraint('Coincident',13,2,1,2)) 
#
this_sketch.setExpression('Constraints[0]', u'sp_footer.dowel_dia')
this_sketch.setExpression('Constraints[14]', u'sp_global.small_tool_dia')#
this_sketch.setExpression('Constraints[17]', u'sp_footer.notch_depth')
this_sketch.setExpression('Constraints[22]', u'sp_standard.length / 2')
this_sketch.addConstraint(Sketcher.Constraint('PointOnObject',14,1,-1)) 
this_sketch.addConstraint(Sketcher.Constraint('Coincident',14,2,1,2)) 
this_sketch.addConstraint(Sketcher.Constraint('Vertical',14)) 
this_sketch.addConstraint(Sketcher.Constraint('Coincident',15,1,2,2)) 
this_sketch.addConstraint(Sketcher.Constraint('Vertical',15)) 
this_sketch.addConstraint(Sketcher.Constraint('Coincident',16,1,15,2)) 
this_sketch.addConstraint(Sketcher.Constraint('Coincident',16,2,14,1)) 
this_sketch.addConstraint(Sketcher.Constraint('Horizontal',16)) 
#
# ---- sk_joist
#
FreeCAD.Console.PrintMessage("Starting busybox_003_sketches --- joist.\n") 
this_sketch = group_sketches.newObject('Sketcher::SketchObject','sk_joist_000')
this_sketch.Placement = App.Placement(App.Vector(0.000000,0.000000,0.000000),App.Rotation(0.500000,0.500000,0.500000,0.500000))
this_sketch.MapMode = 'FlatFace'
this_sketch.addGeometry(Part.LineSegment(App.Vector(19.050000,0.000000,0),App.Vector(38.100000,0.000000,0)),False)
this_sketch.addConstraint(Sketcher.Constraint('PointOnObject',0,1,-1)) 
this_sketch.addConstraint(Sketcher.Constraint('PointOnObject',0,2,-1)) 
this_sketch.addGeometry(Part.LineSegment(App.Vector(38.100000,0.000000,0),App.Vector(38.100000,38.100000,0)),False)
this_sketch.addConstraint(Sketcher.Constraint('Coincident',1,1,0,2)) 
this_sketch.addConstraint(Sketcher.Constraint('Vertical',1)) 
this_sketch.addGeometry(Part.LineSegment(App.Vector(38.100000,38.100000,0),App.Vector(19.050000,38.100000,0)),False)
this_sketch.addConstraint(Sketcher.Constraint('Coincident',2,1,1,2)) 
this_sketch.addConstraint(Sketcher.Constraint('Horizontal',2)) 
this_sketch.addGeometry(Part.LineSegment(App.Vector(19.050000,38.100000,0),App.Vector(19.050000,0.000000,0)),False)
this_sketch.addConstraint(Sketcher.Constraint('Coincident',3,1,2,2)) 
this_sketch.addConstraint(Sketcher.Constraint('Coincident',3,2,0,1)) 
this_sketch.addConstraint(Sketcher.Constraint('Vertical',3)) 
this_sketch.addConstraint(Sketcher.Constraint('DistanceX',-1,1,0,1,19.050000)) 
this_sketch.setExpression('Constraints[9]', u'sp_standard.width')
this_sketch.addConstraint(Sketcher.Constraint('DistanceX',0,1,0,2,19.050000)) 
this_sketch.setExpression('Constraints[10]', u'sp_joist.width')
this_sketch.addConstraint(Sketcher.Constraint('DistanceY',0,2,1,2,38.100000)) 
this_sketch.setExpression('Constraints[11]', u'sp_joist.height')
#
# ---- sk_standardF
#
FreeCAD.Console.PrintMessage("Starting busybox_003_sketches --- standardF.\n") 
this_sketch = group_sketches.newObject('Sketcher::SketchObject','sk_standardF_000')
this_sketch.MapMode = 'FlatFace'
this_sketch.addGeometry(Part.LineSegment(App.Vector(-44.450000,47.625000,0),App.Vector(-6.350000,47.625000,0)),False)
this_sketch.addConstraint(Sketcher.Constraint('Horizontal',0)) 
this_sketch.addGeometry(Part.LineSegment(App.Vector(-44.450000,6.350000,0),App.Vector(-6.350000,6.350000,0)),False)
this_sketch.addConstraint(Sketcher.Constraint('Horizontal',1)) 
this_sketch.addGeometry(Part.LineSegment(App.Vector(6.350000,3.175000,0),App.Vector(6.350000,22.225000,0)),False)
this_sketch.addConstraint(Sketcher.Constraint('Vertical',2)) 
this_sketch.addGeometry(Part.LineSegment(App.Vector(-60.325000,31.750000,0),App.Vector(-60.325000,12.700000,0)),False)
this_sketch.addConstraint(Sketcher.Constraint('Vertical',3)) 
this_sketch.addConstraint(Sketcher.Constraint('DistanceY',2,1,2,2,19.050000)) 
this_sketch.setExpression('Constraints[4]', u'sp_standard.width')
this_sketch.addConstraint(Sketcher.Constraint('DistanceX',1,1,1,2,38.100000)) 
this_sketch.addConstraint(Sketcher.Constraint('Coincident', 3, 1, 0, 1)) 
this_sketch.addConstraint(Sketcher.Constraint('Coincident', 1, 1, 3, 2)) 
this_sketch.addConstraint(Sketcher.Constraint('Coincident', 0, 2, 2, 2)) 
this_sketch.movePoint(0,0,App.Vector(2.002364,5.961937,0),1)
this_sketch.addConstraint(Sketcher.Constraint('Coincident',2,1,1,2)) 
this_sketch.addConstraint(Sketcher.Constraint('Coincident',1,2,-1,1)) 
this_sketch.setExpression('Constraints[5]', u'sp_standard.length')
Gui.activeDocument().resetEdit()
#
#  ----  sk_spacer_notch
#
FreeCAD.Console.PrintMessage("Starting busybox_003_sketches --- spacer_notch.\n") 
aux_sketch = App.activeDocument().group_sketches.newObject('Sketcher::SketchObject','sk_spacer_notch_000')
# Aubrey --- I want to make the z value parametric off of a spreadsheet
#Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
aux_sketch.setExpression('Placement.Base.z', u'sp_joist.height-sp_spacer.notch_depth')
aux_sketch.addGeometry(Part.LineSegment(App.Vector(0.695014,19.050000,0),App.Vector(19.050000,19.050000,0)),False)
aux_sketch.addConstraint(Sketcher.Constraint('PointOnObject',0,1,-2)) 
aux_sketch.addConstraint(Sketcher.Constraint('Horizontal',0)) 
aux_sketch.addGeometry(Part.LineSegment(App.Vector(19.050000,19.050000,0),App.Vector(19.050000,38.100000,0)),False)
aux_sketch.addConstraint(Sketcher.Constraint('Coincident',1,1,0,2)) 
aux_sketch.addConstraint(Sketcher.Constraint('Vertical',1)) 
aux_sketch.addGeometry(Part.LineSegment(App.Vector(19.050000,38.100000,0),App.Vector(0.000000,38.100000,0)),False)
aux_sketch.addConstraint(Sketcher.Constraint('Coincident',2,1,1,2)) 
aux_sketch.addConstraint(Sketcher.Constraint('Horizontal',2)) 
aux_sketch.addGeometry(Part.LineSegment(App.Vector(0.000000,38.100000,0),App.Vector(0.000000,19.050000,0)),False)
aux_sketch.addConstraint(Sketcher.Constraint('Coincident',3,1,2,2)) 
aux_sketch.addConstraint(Sketcher.Constraint('Coincident',3,2,0,1)) 
aux_sketch.addConstraint(Sketcher.Constraint('Vertical',3)) 
aux_sketch.addConstraint(Sketcher.Constraint('DistanceX',2,2,1,2,19.050000)) 
aux_sketch.setDatum(9,App.Units.Quantity('19.050000 mm'))
aux_sketch.addConstraint(Sketcher.Constraint('DistanceY',0,2,1,2,19.050000)) 
aux_sketch.setDatum(10,App.Units.Quantity('19.050000 mm'))
aux_sketch.addConstraint(Sketcher.Constraint('DistanceY',-1,1,0,1,19.050000)) 
aux_sketch.setDatum(11,App.Units.Quantity('19.050000 mm'))
aux_sketch.setExpression('Constraints[9]', u'sp_spacer.width')
aux_sketch.setExpression('Constraints[10]', u'sp_joist.width')
aux_sketch.setExpression('Constraints[11]', u'sp_standard.width')
#
#  ----  sk_spacer_body
#
FreeCAD.Console.PrintMessage("Starting busybox_003_sketches --- spacer_body.\n") 
this_sketch = App.activeDocument().group_sketches.newObject('Sketcher::SketchObject','sk_spacer_body_000')
this_sketch.Placement = App.Placement(App.Vector(0, 0, 0), \
    App.Rotation(-0.707107,0.000000,0.000000,-0.707107))
#this_sketch.setExpression('Placement.Base.x', u'sp_spacer.width')
#this_sketch.setExpression('Placement.Base.z', u'sp_joist.height-sp_spacer.height')
#
this_sketch.addGeometry(Part.LineSegment(App.Vector(19.050000,0.000000,0),App.Vector(38.100000,0.000000,0)),False)
#this_sketch.addConstraint(Sketcher.Constraint('Horizontal',0)) 
this_sketch.addGeometry(Part.LineSegment(App.Vector(38.100000,0.000000,0),App.Vector(38.100000,38.100000,0)),False)
this_sketch.addConstraint(Sketcher.Constraint('Coincident',1,1,0,2)) 
this_sketch.addConstraint(Sketcher.Constraint('Vertical',1)) 
this_sketch.addGeometry(Part.LineSegment(App.Vector(38.100000,38.100000,0),App.Vector(19.050000,38.100000,0)),False)
this_sketch.addConstraint(Sketcher.Constraint('Coincident',2,1,1,2)) 
this_sketch.addConstraint(Sketcher.Constraint('Horizontal',2)) 
this_sketch.addGeometry(Part.LineSegment(App.Vector(19.050000,38.100000,0),App.Vector(19.050000,0.000000,0)),False)
this_sketch.addConstraint(Sketcher.Constraint('Coincident',3,1,2,2)) 
this_sketch.addConstraint(Sketcher.Constraint('Coincident',3,2,0,1)) 
this_sketch.addConstraint(Sketcher.Constraint('Vertical',3)) 
this_sketch.addConstraint(Sketcher.Constraint('DistanceY',0,2,1,2,38.100000)) 
this_sketch.setExpression('Constraints[7]', u'sp_spacer.height')
this_sketch.addConstraint(Sketcher.Constraint('Horizontal',0)) 
this_sketch.addConstraint(Sketcher.Constraint('DistanceX',0,1,0,2,19.050000)) 
this_sketch.setExpression('Constraints[9]', u'sp_spacer.width')
this_sketch.addConstraint(Sketcher.Constraint('DistanceY',-1,1,2,2,26.715581)) 
this_sketch.setExpression('Constraints[10]', u'sp_joist.height')
this_sketch.addConstraint(Sketcher.Constraint('PointOnObject',2,2,-2)) 
#
Gui.activeDocument().resetEdit()
# Macro End: $HOME/Documents/FreeCAD/Busybox/busybox_003_sketches.FCMacro +++++++++++++++++++++++++++++++++++++++++++++++++

#
#  ----  sk_support_body
#
# -*- coding: utf-8 -*-

# Macro Begin: /home/amcintosh/Documents/FreeCAD/Busybox/Macro/support2.FCMacro +++++++++++++++++++++++++++++++++++++++++++++++++
this_support = App.activeDocument().addObject('Sketcher::SketchObject','sk_support_000')
App.activeDocument().sk_support_000.Placement = App.Placement(App.Vector(0.000000,0.000000,0.000000),App.Rotation(-0.707107,0.000000,0.000000,-0.707107))
App.activeDocument().sk_support_000.MapMode = "Deactivated"
#
#this_support = App.activeDocument().getObject('sk_support_000')
this_support.addGeometry(Part.LineSegment(App.Vector(3.175,-9.525,0),App.Vector(3.175,-0.045601,0)),True)
this_support.addGeometry(Part.LineSegment(App.Vector(3.175, 0, 0),App.Vector(-13.902,4.26928,0)),True)
this_support.addGeometry(Part.ArcOfCircle(Part.Circle(App.Vector(-14.287500,2.729177,0),App.Vector(0,0,1),1.587500),1.325822,3.141593),True)
this_support.addGeometry(Part.LineSegment(App.Vector(-15.875,2.7292,0),App.Vector(-15.875,-12.254,0)),True)
this_support.addGeometry(Part.ArcOfCircle(Part.Circle(App.Vector(-14.2875,-12.254381,0),App.Vector(0,0,1),1.587500),3.141593,4.957363),True)
this_support.addGeometry(Part.LineSegment(App.Vector(-13.90248,-13.79448,0),App.Vector(3.175,-9.525,0)),True)
this_support.addGeometry(Part.Point(App.Vector(-15.875,4.762,0)))
this_support.addGeometry(Part.Point(App.Vector(-15.875,-14.2876,0)))
this_support.addGeometry(Part.Point(App.Vector(-15.83,-5.18,0)))
this_support.addGeometry(Part.Point(App.Vector(3.175,-5.18,0)))
#
#  --------
#
this_support.addConstraint(Sketcher.Constraint('DistanceX',7,1,0,1,19.05)) 
this_support.addConstraint(Sketcher.Constraint('DistanceY',7,1,6,1,19.05)) 
this_support.addConstraint(Sketcher.Constraint('DistanceX',-1,1,0,2,3.175)) 
this_support.addConstraint(Sketcher.Constraint('Parallel',3,0))
this_support.addConstraint(Sketcher.Constraint('Vertical',0)) 


this_support.addConstraint(Sketcher.Constraint('Coincident',1,1,0,2)) 
this_support.addConstraint(Sketcher.Constraint('Tangent',2,1,1,2)) 
this_support.addConstraint(Sketcher.Constraint('Tangent',2,2,3,1)) 
this_support.addConstraint(Sketcher.Constraint('PointOnObject',6,1,1))
this_support.addConstraint(Sketcher.Constraint('PointOnObject',6,1,3))
this_support.addConstraint(Sketcher.Constraint('Tangent',3,2,4,1)) 
this_support.addConstraint(Sketcher.Constraint('Tangent',4,2,5,1)) 
this_support.addConstraint(Sketcher.Constraint('PointOnObject',7,1,3)) 
this_support.addConstraint(Sketcher.Constraint('PointOnObject',7,1,5)) 
this_support.addConstraint(Sketcher.Constraint('Coincident',5,2,0,1))

this_support.addConstraint(Sketcher.Constraint('PointOnObject',0,2,-1)) 

this_support.addConstraint(Sketcher.Constraint('Diameter',2,3.175)) 
this_support.addConstraint(Sketcher.Constraint('Equal',2,4)) 

this_support.addConstraint(Sketcher.Constraint('Symmetric',0,2,0,1,9,1)) 
this_support.addConstraint(Sketcher.Constraint('Symmetric',6,1,7,1,8,1)) 
this_support.addConstraint(Sketcher.Constraint('DistanceY',0,1,0,2,9.578633)) 
this_support.addConstraint(Sketcher.Constraint('Horizontal',8,1,9,1))
#
this_support.setExpression('Constraints[0]', u'sp_global.wood_stock_thickness')
this_support.setExpression('Constraints[1]', u'sp_support.height')
this_support.setExpression('Constraints[2]', u'sp_support.key_height')
this_support.setExpression('Constraints[16]', u'sp_global.small_tool_dia')
this_support.setExpression('Constraints[20]', u'sp_support.face_size')
#
this_support.toggleConstruction(0) 
this_support.toggleConstruction(1) 
this_support.toggleConstruction(4) 
this_support.toggleConstruction(2) 
this_support.toggleConstruction(5) 
this_support.toggleConstruction(3) 
App.ActiveDocument.recompute()
App.ActiveDocument.getObject('group_sketches').Group += [this_support,]
# Macro End: /home/amcintosh/Documents/FreeCAD/Busybox/Macro/support3.FCMacro +++++++++++++++++++++++++++++++++++++++++++++++++#
#  ---- dovetail top
#
# -*- coding: utf-8 -*-

# Macro Begin: /home/amcintosh/Documents/FreeCAD/Busybox/Macro/aa_dovetail_2.FCMacro +++++++++++++++++++++++++++++++++++++++++++++++++
import FreeCAD
import Sketcher
import math

FreeCAD.Console.PrintMessage("Starting busybox_003_sketches --- dovetail_top.\n")
offset = \
  float(App.ActiveDocument.sp_joist.get(App.ActiveDocument.sp_joist.getCellFromAlias("height"))) \
  -float(App.ActiveDocument.sp_spacer.get(App.ActiveDocument.sp_spacer.getCellFromAlias("height")))
aux_v1 = App.Vector(0, 0, 0)
aux_v1.x = float(App.ActiveDocument.sp_joist.get(App.ActiveDocument.sp_joist.getCellFromAlias("width")))
aux_v1.y = math.tan(20 * math.pi / 180) * aux_v1.x

aux_v2 = App.Vector(0, 0, 0)
aux_v2.x = float(App.ActiveDocument.sp_joist.get(App.ActiveDocument.sp_joist.getCellFromAlias("width")))
aux_v2.y = float(App.ActiveDocument.sp_spacer.get(App.ActiveDocument.sp_spacer.getCellFromAlias("height")))

p1 = App.Vector(aux_v1.x, aux_v1.y + offset, 0)
p2 = App.Vector(aux_v1.x, aux_v2.y + offset, 0)
p3 = App.Vector(0, aux_v2.y + offset, 0)
p4 = App.Vector(0, 0 + offset, 0)

this_sketch = App.activeDocument().addObject('Sketcher::SketchObject','sk_dovetail_top_000')
this_sketch.Placement = App.Placement(App.Vector(0.000000,0.000000,0.000000),App.Rotation(0.500000,0.500000,0.500000,0.500000))
this_sketch.MapMode = "Deactivated"
this_sketch.addGeometry(Part.LineSegment(p1,p2),False)
this_sketch.addGeometry(Part.LineSegment(p2,p3),False)
this_sketch.addGeometry(Part.LineSegment(p3,p4),False)
this_sketch.addGeometry(Part.LineSegment(p4,p1),False)

this_sketch.addConstraint(Sketcher.Constraint('Vertical',0)) 
this_sketch.addConstraint(Sketcher.Constraint('Horizontal',1)) 
this_sketch.addConstraint(Sketcher.Constraint('Vertical',2)) 

FreeCAD.Console.PrintMessage("Starting busybox_003_sketches --- dovetail_top. line 519\n")
this_sketch.addConstraint(Sketcher.Constraint('Coincident',0,2,1,1)) 
this_sketch.addConstraint(Sketcher.Constraint('Coincident',1,2,2,1)) 
this_sketch.addConstraint(Sketcher.Constraint('Coincident',2,2,3,1)) 
this_sketch.addConstraint(Sketcher.Constraint('Coincident',3,2,0,1)) 

this_sketch.addConstraint(Sketcher.Constraint('Angle',3,2,2,1,math.pi/2 - 20 * math.pi / 180)) 
this_sketch.addConstraint(Sketcher.Constraint('PointOnObject',2,2,-2)) 
this_sketch.addConstraint(Sketcher.Constraint('DistanceY',-1,1,2,2,offset)) 
this_sketch.addConstraint(Sketcher.Constraint('DistanceX',1,2,1,1,aux_v1.x)) 
this_sketch.addConstraint(Sketcher.Constraint('DistanceY',2,2,2,1,aux_v2.y))

App.ActiveDocument.group_sketches.Group += [this_sketch, ]
#
#  ---- dovetail bottom
#
# Macro End: /home/amcintosh/Documents/FreeCAD/Busybox/Macro/aa_dovetail_2.FCMacro +++++++++++++++++++++++++++++++++++++++++++++++++# -*- coding: utf-8 -*-

# Macro Begin: /home/amcintosh/Documents/FreeCAD/Busybox/Macro/aa_dovetail_2.FCMacro +++++++++++++++++++++++++++++++++++++++++++++++++
FreeCAD.Console.PrintMessage("Starting busybox_003_sketches --- dovetail_bottom.\n")
import FreeCAD
import Sketcher
import math

offset = \
  float(App.ActiveDocument.sp_joist.get(App.ActiveDocument.sp_joist.getCellFromAlias("height"))) \
  -float(App.ActiveDocument.sp_spacer.get(App.ActiveDocument.sp_spacer.getCellFromAlias("height")))
aux_v = App.Vector(0, 0, 0)
aux_v.x = float(App.ActiveDocument.sp_joist.get(App.ActiveDocument.sp_joist.getCellFromAlias("width")))
aux_v.y = math.tan(20 * math.pi / 180) * aux_v.x

p1 = App.Vector(aux_v.x, 0 + offset, 0)
p2 = App.Vector(aux_v.x, aux_v.y + offset, 0)
p3 = App.Vector(0, 0 + offset, 0)

this_sketch = App.activeDocument().addObject('Sketcher::SketchObject','sk_dovetail_bottom_000')
this_sketch.Placement = App.Placement(App.Vector(0.000000,0.000000,0.000000),App.Rotation(0.500000,0.500000,0.500000,0.500000))
this_sketch.MapMode = "Deactivated"
this_sketch.addGeometry(Part.LineSegment(p1,p2),False)
this_sketch.addConstraint(Sketcher.Constraint('Vertical',0)) 
this_sketch.addGeometry(Part.LineSegment(p2,p3),False)
this_sketch.addConstraint(Sketcher.Constraint('Coincident',0,2,1,1)) 
this_sketch.addGeometry(Part.LineSegment(p3,p1),False)
this_sketch.addConstraint(Sketcher.Constraint('DistanceX',2,1,0,1,aux_v.x)) 
this_sketch.addConstraint(Sketcher.Constraint('Horizontal',2)) 
this_sketch.addConstraint(Sketcher.Constraint('Coincident',1,2,2,1)) 
this_sketch.addConstraint(Sketcher.Constraint('Coincident',2,2,0,1)) 
this_sketch.addConstraint(Sketcher.Constraint('Angle',2,2,1,1,0.349066)) 
this_sketch.addConstraint(Sketcher.Constraint('PointOnObject',2,1,-2)) 
this_sketch.addConstraint(Sketcher.Constraint('DistanceY',-1,1,1,2,offset)) 

App.ActiveDocument.group_sketches.Group += [this_sketch, ]
Gui.activeDocument().activeView().viewIsometric()
Gui.SendMsgToActiveView("ViewFit")

aux_height_item = (App.ActiveDocument.sp_standard.get(App.ActiveDocument.sp_standard.getCellFromAlias("item_height")))
aux_height_joist = (App.ActiveDocument.sp_joist.get(App.ActiveDocument.sp_joist.getCellFromAlias("height")))
aux_support_face = (App.ActiveDocument.sp_support.get(App.ActiveDocument.sp_support.getCellFromAlias("face_size")))
aux_shelf_count = int(App.ActiveDocument.sp_standard.get(App.ActiveDocument.sp_standard.getCellFromAlias("shelf_count")))
aux_elevation = (App.ActiveDocument.sp_global.get(App.ActiveDocument.sp_global.getCellFromAlias("first_shelf_elevation")))
aux_height_footer = (App.ActiveDocument.sp_footer.get(App.ActiveDocument.sp_footer.getCellFromAlias("height")))
aux_notch_depth = (App.ActiveDocument.sp_footer.get(App.ActiveDocument.sp_footer.getCellFromAlias("notch_depth")))
aux_extension_length = aux_elevation - aux_height_joist - aux_height_footer + aux_notch_depth
aux_face_size = (App.ActiveDocument.sp_support.get(App.ActiveDocument.sp_support.getCellFromAlias("face_size")))
length = (aux_shelf_count-1)*(aux_height_item+aux_height_joist)
FreeCAD.Console.PrintMessage("busybox_003_unified_sketches, line 467\n ---> pattern length:\t" + str(length) + "\n")
FreeCAD.Console.PrintMessage("busybox_003_unified_sketches, line 468\n ---> aux_extension_length:\t" + str(aux_extension_length) + "\n")
FreeCAD.Console.PrintMessage("busybox_003_unified_sketches, line 469\n ---> adjusted aux_extension_length:\t" + str(aux_extension_length+aux_face_size) + "\n")
aux_length = length + aux_extension_length - aux_face_size
FreeCAD.Console.PrintMessage("busybox_003_unified_sketches, line 470\n\n ---> spreadsheet length value:\t" + str(aux_length) + "\n\n")
App.ActiveDocument.sp_standard.set('B4', str(aux_length))	#was 84".  Changed to make part symmetric, adjusted joist height.
#
#  --  sk_spacer_notchH_000
#
this_sketch = App.activeDocument().addObject('Sketcher::SketchObject','sk_spacer_notchH_000')
this_sketch.Placement = App.Placement(App.Vector(0.000000,0.000000,0.000000),App.Rotation(-0.707107,0.000000,0.000000,-0.707107))
this_sketch.MapMode = "Deactivated"
#
this_sketch.addGeometry(Part.Point(App.Vector(19.050000,15.875000,0)))
this_sketch.addGeometry(Part.Point(App.Vector(19.050000,17.462500,0)))
this_sketch.addGeometry(Part.LineSegment(App.Vector(19.050000,17.462500,0),App.Vector(19.050000,19.050000,0)),False)
this_sketch.addGeometry(Part.LineSegment(App.Vector(0.000000,19.050000,0),App.Vector(19.050000,19.050000,0)),False)
this_sketch.addGeometry(Part.LineSegment(App.Vector(0.000000,19.050000,0),App.Vector(0.000000,17.462500,0)),False)
this_sketch.addGeometry(Part.LineSegment(App.Vector(1.587500,15.875000,0),App.Vector(17.462500,15.875000,0)),False)
this_sketch.addGeometry(Part.ArcOfCircle(Part.Circle(App.Vector(17.462500,17.462500,0),App.Vector(0,0,1),1.587500),-1.570796,0.000000),False)
this_sketch.addGeometry(Part.ArcOfCircle(Part.Circle(App.Vector(1.587500,17.462500,0),App.Vector(0,0,1),1.587500),3.141593,4.712389),False)
this_sketch.addGeometry(Part.LineSegment(App.Vector(19.050000,0.000000,0),App.Vector(19.050000,17.462502,0)),True)
this_sketch.addGeometry(Part.LineSegment(App.Vector(0.000000,17.462502,0),App.Vector(0.000000,0.000000,0)),True)
this_sketch.addGeometry(Part.LineSegment(App.Vector(0.000000,0.000000,0),App.Vector(19.050000,0.000000,0)),True)

this_sketch.addConstraint(Sketcher.Constraint('Coincident',2,1,1,1)) 
this_sketch.addConstraint(Sketcher.Constraint('Vertical',2)) 
this_sketch.addConstraint(Sketcher.Constraint('PointOnObject',3,1,-2)) 
this_sketch.addConstraint(Sketcher.Constraint('Coincident',3,2,2,2)) 
this_sketch.addConstraint(Sketcher.Constraint('Horizontal',3)) 
this_sketch.addConstraint(Sketcher.Constraint('Coincident',4,1,3,1)) 
this_sketch.addConstraint(Sketcher.Constraint('Vertical',4)) 
this_sketch.addConstraint(Sketcher.Constraint('Horizontal',5)) 
this_sketch.addConstraint(Sketcher.Constraint('Coincident',6,2,1,1)) 
this_sketch.addConstraint(Sketcher.Constraint('Diameter',6,3.175000)) 
this_sketch.addConstraint(Sketcher.Constraint('Equal',6,7)) 
this_sketch.addConstraint(Sketcher.Constraint('DistanceY',5,2,2,2,3.175000)) 
this_sketch.delGeometry(0)
this_sketch.addConstraint(Sketcher.Constraint('DistanceX',2,1,1,2,19.050000)) 
this_sketch.addConstraint(Sketcher.Constraint('DistanceY',-1,1,4,1,15.875000)) 
this_sketch.addConstraint(Sketcher.Constraint('Tangent',6,1,3,2)) 
this_sketch.addConstraint(Sketcher.Constraint('Tangent',6,2,4,1)) 
this_sketch.addConstraint(Sketcher.Constraint('Tangent',5,1,4,2)) 
this_sketch.addConstraint(Sketcher.Constraint('TangentViaPoint',5,1,1,1)) 
this_sketch.addConstraint(Sketcher.Constraint('PointOnObject',7,1,-1)) 
this_sketch.addConstraint(Sketcher.Constraint('Coincident',7,2,0,1)) 
this_sketch.addConstraint(Sketcher.Constraint('Vertical',7)) 
this_sketch.addConstraint(Sketcher.Constraint('Coincident',8,1,3,2)) 
this_sketch.addConstraint(Sketcher.Constraint('Coincident',8,2,-1,1)) 
this_sketch.addConstraint(Sketcher.Constraint('Coincident',9,1,-1,1)) 
this_sketch.addConstraint(Sketcher.Constraint('Coincident',9,2,7,1)) 

this_sketch.setExpression('Constraints[9]', u'sp_global.small_tool_dia')
this_sketch.setExpression('Constraints[11]', u'2 * sp_spacer.notch_depth')
this_sketch.setExpression('Constraints[12]', u'sp_spacer.width')
this_sketch.setExpression('Constraints[13]', u'sp_joist.height - sp_spacer.notch_depth')
App.ActiveDocument.getObject('group_sketches').Group += [this_sketch,]
#
#  --  sk_skirt_path_000
#
this_sketch = App.activeDocument().addObject('Sketcher::SketchObject','sk_skirt_path_000')
this_sketch.Placement = App.Placement(App.Vector(0.000000,0.000000,0.000000),App.Rotation(0.500000,0.500000,0.500000,0.500000))
this_sketch.addGeometry(Part.LineSegment(App.Vector(0.000000,12.700000,0),App.Vector(19.050000,15.875000,0)),False)
this_sketch.addGeometry(Part.LineSegment(App.Vector(19.050000,15.875000,0),App.Vector(29.368750,17.462500,0)),False)
this_sketch.addConstraint(Sketcher.Constraint('PointOnObject',0,2,-2)) 
this_sketch.addConstraint(Sketcher.Constraint('Coincident',1,1,0,1)) 
this_sketch.addConstraint(Sketcher.Constraint('Parallel',1,0)) 
this_sketch.addConstraint(Sketcher.Constraint('DistanceY',0,2,0,1,3.089189)) 
this_sketch.setExpression('Constraints[3]', u'sp_joist.notch_depth')
this_sketch.addConstraint(Sketcher.Constraint('DistanceY',-1,1,0,2,12.567708)) 
this_sketch.setExpression('Constraints[4]', u'sp_joist.height - 2 * sp_joist.notch_depth')
this_sketch.addConstraint(Sketcher.Constraint('DistanceX',0,1,1,2,10.318750)) 
this_sketch.setExpression('Constraints[5]', u'sp_joist.width / 2')
this_sketch.addConstraint(Sketcher.Constraint('DistanceX',-1,1,0,1,13.711896)) 
this_sketch.setExpression('Constraints[6]', u'sp_joist.width')
#
App.ActiveDocument.sk_skirt_path_000.delGeometry(1)
App.ActiveDocument.sk_skirt_path_000.addGeometry(Part.ArcOfCircle(Part.Circle(App.Vector(17.472805,1.464441,0),App.Vector(0,0,1),14.496611),1.461783,1.802285),True)
App.ActiveDocument.sk_skirt_path_000.addConstraint(Sketcher.Constraint('Coincident',1,1,0,1)) 
App.ActiveDocument.sk_skirt_path_000.addGeometry(Part.LineSegment(App.Vector(0.000000,12.700000,0),App.Vector(-4.054002,9.525000,0)),True)
App.ActiveDocument.sk_skirt_path_000.addConstraint(Sketcher.Constraint('Coincident',2,1,0,2)) 
App.ActiveDocument.sk_skirt_path_000.addGeometry(Part.LineSegment(App.Vector(14.146894,15.875000,0),App.Vector(0.000000,12.700000,0)),True)
App.ActiveDocument.sk_skirt_path_000.addConstraint(Sketcher.Constraint('Coincident',3,1,1,2)) 
App.ActiveDocument.sk_skirt_path_000.addConstraint(Sketcher.Constraint('Coincident',3,2,0,2)) 
App.ActiveDocument.sk_skirt_path_000.delGeometry(0)
App.ActiveDocument.sk_skirt_path_000.addGeometry(Part.LineSegment(App.Vector(-4.054002,9.525000,0),App.Vector(0.000000,0.000000,0)),True)
App.ActiveDocument.sk_skirt_path_000.addConstraint(Sketcher.Constraint('Coincident',3,1,1,2)) 
App.ActiveDocument.sk_skirt_path_000.addConstraint(Sketcher.Constraint('Coincident',3,2,-1,1)) 
App.ActiveDocument.sk_skirt_path_000.addConstraint(Sketcher.Constraint('Perpendicular',2,3)) 
App.ActiveDocument.sk_skirt_path_000.addConstraint(Sketcher.Constraint('PointOnObject',1,2,2)) 
App.ActiveDocument.sk_skirt_path_000.addConstraint(Sketcher.Constraint('Coincident',2,2,1,1)) 
App.ActiveDocument.sk_skirt_path_000.addConstraint(Sketcher.Constraint('Tangent',2,1,0,2)) 
App.ActiveDocument.sk_skirt_path_000.delConstraintOnPoint(2,1)
App.ActiveDocument.sk_skirt_path_000.addConstraint(Sketcher.Constraint('Vertical',0,3,0,1)) 
App.ActiveDocument.sk_skirt_path_000.addConstraint(Sketcher.Constraint('Horizontal',-1,1,0,3)) 
App.ActiveDocument.sk_skirt_path_000.toggleConstruction(2) 
App.ActiveDocument.sk_skirt_path_000.toggleConstruction(0) 
App.ActiveDocument.sk_skirt_path_000.toggleConstruction(1) 
#
App.ActiveDocument.getObject('group_sketches').Group += [this_sketch,]
# Macro End: /home/amcintosh/Documents/FreeCAD/Busybox/Macro/aa_dovetail_2.FCMacro +++++++++++++++++++++++++++++++++++++++++++++++++
