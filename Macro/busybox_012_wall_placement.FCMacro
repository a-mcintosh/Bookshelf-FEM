#  --------------------------------------------------------
#  -- Copyright (c) 2020-06-24 by Aubrey McIntosh, PhD   --
#  -- Permission granted for use in educational settings --
#  -- and personal study with this notice left intact.   --
#  --------------------------------------------------------

aux_part = App.activeDocument().Wall_
aux_part.setExpression('Placement.Base.x', u'sp_joist.length+sp_spacer.width')
aux_part.setExpression('Placement.Base.y', u'sp_footer.length+sp_joist.width')

this_rot = App.Rotation(App.Vector(0, 0, 1), 180)
aux_part.Placement.Rotation = this_rot.multiply(aux_part.Placement.Rotation)
Gui.activeDocument().hide('prototypes_of_bodies_1')
