#  --------------------------------------------------------
#  -- Copyright (c) 2020-06-24 by Aubrey McIntosh, PhD   --
#  -- Permission granted for use in educational settings --
#  -- and personal study with this notice left intact.   --
#  --------------------------------------------------------

# ----------------------------
Gui.activeDocument().activeView().setCamera('#Inventor V2.1 ascii\n\n\nOrthographicCamera {\n  viewportMapping ADJUST_CAMERA\n  position 276.51953 -1670.4697 1319.3772\n  orientation 0.89191508 0.26466164 0.36666301  1.3355073\n  nearDistance -1576.964\n  farDistance 3201.3433\n  aspectRatio 1\n  focalDistance 1343.21\n  height 4007.6709\n\n}\n')
Gui.activeDocument().show(App.ActiveDocument.prototypes_of_bodies_1.Name)
Gui.activeDocument().hide(App.ActiveDocument.prototypes_of_bodies_1.Name)

this_doc = App.ActiveDocument
# -- Shelf
this_doc.Shelf_002.Placement.Base.x = -25.4 * (60 + 1.5)
this_doc.Shelf_002.Placement.Base.y = -25.4 * (20.75)
this_doc.Support_002.Placement.Base.x = -25.4 * (60 + 1.5)
this_doc.Support_002.Placement.Base.y = -25.4 * (20.75)


this_doc.Support_002.Placement.Base.z = this_doc.Shelf_002.Placement.Base.z
this_doc.explode_skirt_002.Placement.Base.z = 0 + 25.4 * 12
this_doc.explode_joist_002.Placement.Base.z = 25.4 * 24
this_doc.explode_spacer_002.Placement.Base.z = 25.4 * 36
# ----------------------------
# -- Wall
this_doc.Wall_001.Placement.Base.x = -25.4 * (60 + 1.5 + 24)
this_doc.Wall_001.Placement.Base.y = -25.4 * (2*20.75)
this_doc.bd_footer_003001.Placement.Base.z = (80.875 + 15) * 25.4
this_doc.bd_footer_002001.Placement.Base.z = -25.4 * 15
# -- Wall
this_doc.Wall_.Placement.Base.x = 25.4 * (48.75 + 24)
this_doc.Wall_.Placement.Base.y = 25.4 * (20.75 + 20.75)
this_doc.bd_footer_003001.Placement.Base.z = (80.875 + 15) * 25.4
this_doc.bd_footer_002001.Placement.Base.z = -25.4 * 15
# ----------------------------
