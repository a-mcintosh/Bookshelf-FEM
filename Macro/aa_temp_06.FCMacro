# -*- coding: utf-8 -*-

# Macro Begin: /home/amcintosh/Documents/FreeCAD/Busybox/Macro/aa_temp_06.FCMacro +++++++++++++++++++++++++++++++++++++++++++++++++
import FreeCAD
import Sketcher

ActiveSketch.addConstraint(Sketcher.Constraint('DistanceX',19,1,22,1,9.633817)) 
ActiveSketch.setExpression('Constraints[94]', u'sp_support.recess')
ActiveSketch.addConstraint(Sketcher.Constraint('DistanceY',22,1,18,1,4.014115)) 
ActiveSketch.setExpression('Constraints[95]', u'sp_support.key_height')
#ActiveSketch = App.ActiveDocument.getObject('Sketch001')
#tv = ActiveSketch.ViewObject.TempoVis
#if tv:
#  tv.restore()
#ActiveSketch.ViewObject.TempoVis = None
#del(tv)
#
#Gui.SendMsgToActiveView("ViewFit")
#ActiveSketch = App.ActiveDocument.getObject('Sketch001')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch001')
#if ActiveSketch.ViewObject.RestoreCamera:
#  ActiveSketch.ViewObject.TempoVis.saveCamera()
#
#Gui.SendMsgToActiveView("ViewFit")
ActiveSketch.addConstraint(Sketcher.Constraint('Horizontal',19,1,22,1)) 
ActiveSketch.addConstraint(Sketcher.Constraint('Horizontal',22,1,16,1)) 
#ActiveSketch.addConstraint(Sketcher.Constraint('Vertical',22,1,12,1)) #99
#Gui.SendMsgToActiveView("ViewFit")
ActiveSketch.movePoint(22,1,App.Vector(0.000000,0.000000,0),0)
ActiveSketch.movePoint(22,1,App.Vector(0.674556,0.405759,0),0)
ActiveSketch.movePoint(22,1,App.Vector(2.863921,1.603107,0),0)
ActiveSketch.movePoint(22,1,App.Vector(3.638549,1.965331,0),0)
ActiveSketch.addConstraint(Sketcher.Constraint('Perpendicular',50,25)) 
ActiveSketch.movePoint(22,1,App.Vector(2.640802,-2.979046,0),0)
ActiveSketch.movePoint(21,1,App.Vector(-7.112441,2.398910,0),0)
ActiveSketch.movePoint(21,1,App.Vector(-4.943318,2.606479,0),0)
ActiveSketch.addConstraint(Sketcher.Constraint('Vertical',21,1,19,1)) 
ActiveSketch.addConstraint(Sketcher.Constraint('Horizontal',18,1,21,1)) 
#Gui.SendMsgToActiveView("Save")
#App.getDocument("BusyBox_ver_1_1_3").save()
ActiveSketch.movePoint(48,0,App.Vector(-1.093822,-4.192989,0),1)
ActiveSketch.movePoint(48,0,App.Vector(-0.182304,1.093821,0),1)
ActiveSketch.movePoint(49,0,App.Vector(-1.093822,-1.002672,0),1)
ActiveSketch.movePoint(23,0,App.Vector(0.182303,0.000000,0),1)
ActiveSketch.movePoint(24,0,App.Vector(0.455762,-1.184975,0),1)
ActiveSketch.movePoint(50,0,App.Vector(-0.455759,-1.731886,0),1)
ActiveSketch.movePoint(46,0,App.Vector(0.091153,-0.182303,0),1)
ActiveSketch.movePoint(46,0,App.Vector(-2.096495,1.367280,0),1)
ActiveSketch.movePoint(15,1,App.Vector(27.555843,-4.776453,0),0)
ActiveSketch.movePoint(16,1,App.Vector(22.451336,-6.599492,0),0)
ActiveSketch.movePoint(14,1,App.Vector(5.543345,-28.599852,0),0)
ActiveSketch.movePoint(22,1,App.Vector(5.773998,-5.505811,0),0)
#ActiveSketch.addConstraint(Sketcher.Constraint('Vertical',22,1,12,1)) 
ActiveSketch.movePoint(14,1,App.Vector(8.339738,-36.616718,0),0)
ActiveSketch.movePoint(14,1,App.Vector(5.787479,-40.353947,0),0)
ActiveSketch.movePoint(22,1,App.Vector(4.335227,-18.036386,0),0)
ActiveSketch.movePoint(22,1,App.Vector(2.945421,-21.261719,0),0)
ActiveSketch.movePoint(22,1,App.Vector(6.159522,-21.689350,0),0)
ActiveSketch.addConstraint(Sketcher.Constraint('Vertical',18,1,22,1)) 
ActiveSketch.toggleConstruction(51) 
ActiveSketch.toggleConstruction(30) 
ActiveSketch.toggleConstruction(46) 
ActiveSketch.toggleConstruction(35) 
ActiveSketch.toggleConstruction(47) 
ActiveSketch.toggleConstruction(40) 
ActiveSketch.toggleConstruction(48) 
ActiveSketch.toggleConstruction(45) 
ActiveSketch.toggleConstruction(49) 
ActiveSketch.toggleConstruction(50) 
App.ActiveDocument.recompute()
# Macro End: /home/amcintosh/Documents/FreeCAD/Busybox/Macro/aa_temp_06.FCMacro +++++++++++++++++++++++++++++++++++++++++++++++++
