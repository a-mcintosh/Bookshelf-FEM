#  --------------------------------------------------------
#  -- Copyright © 2020-06-24 by Aubrey McIntosh, PhD   --
#  -- Permission granted for use in educational settings --
#  -- and personal study with this notice left intact.   --
#  --------------------------------------------------------
FreeCAD.Console.PrintMessage("\nCopyright © 2020-06-24 by Aubrey McIntosh, PhD\n\n")
Name = 'Shelves_ver_2_3_temp'

# -*- coding: utf-8 -*-

# Macro Begin: $HOME/Documents/FreeCAD/Shelves/busybox_001_start.FCMacro +++++++++++++++++++++++++++++++++++++++++++++++++
import FreeCAD
import PartDesignGui
import Sketcher
#import Show.TempoVis
import PartDesign

# ----------------
# -- Shelves
# -- Goals:
# -- Localize concept to AustinCustomCNC facility
# --
# -- Problems
# -- 
# ----------------
App.newDocument(Name).saveAs(u"/home/amcintosh/Documents/FreeCAD/Shelves/Documents/" + Name + ".FCStd")
FreeCAD.Console.PrintMessage(Name + "\n")
FreeCAD.Console.PrintMessage("Execute the macros in their numbered sequence.\n")
FreeCAD.Console.PrintMessage("Execute the wall macro two times.  You can execute the placement macro between times.\n")
FreeCAD.Console.PrintMessage("\n------------------------\n")
FreeCAD.Console.PrintMessage("import shelf_nr now\n")
FreeCAD.Console.PrintMessage("------------------------\n\n")

# Macro End: $HOME/Documents/FreeCAD/Shelves/busybox_001_start.FCMacro +++++++++++++++++++++++++++++++++++++++++++++++++
