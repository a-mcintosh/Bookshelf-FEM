# -*- coding: utf-8 -*-

# Macro Begin: /home/amcintosh/Documents/FreeCAD/Busybox/Macro/aa_temp_04.FCMacro +++++++++++++++++++++++++++++++++++++++++++++++++
import FreeCAD
import Sketcher

ActiveSketch.addGeometry(Part.LineSegment(App.Vector(19.049999,0.836061,0),App.Vector(20.637501,2.427051,0)),True)
ActiveSketch.addGeometry(Part.LineSegment(App.Vector(20.637501,2.427051,0),App.Vector(20.450228,3.252028,0)),True)
ActiveSketch.addGeometry(Part.LineSegment(App.Vector(20.419102,3.195044,0),App.Vector(19.049999,3.175000,0)),True)
ActiveSketch.addGeometry(Part.LineSegment(App.Vector(19.049999,3.175000,0),App.Vector(19.049999,0.836061,0)),True)
ActiveSketch.addGeometry(Part.ArcOfCircle(Part.Circle(App.Vector(19.049999,0.836061,0),App.Vector(0,0,1),2.247534),0.786496,1.570796),True)
ActiveSketch.addConstraint(Sketcher.Constraint('Coincident',30,2,2,1)) 
ActiveSketch.addConstraint(Sketcher.Constraint('Coincident',17,1,28,1)) 
ActiveSketch.addConstraint(Sketcher.Constraint('Coincident',2,1,28,2)) 
ActiveSketch.addConstraint(Sketcher.Constraint('Coincident',2,1,29,1)) 
ActiveSketch.addConstraint(Sketcher.Constraint('Perpendicular',27,26)) 
ActiveSketch.addConstraint(Sketcher.Constraint('Perpendicular',28,29)) 
ActiveSketch.addConstraint(Sketcher.Constraint('Coincident',26,2,1,1)) 
ActiveSketch.addConstraint(Sketcher.Constraint('Coincident',26,2,27,1)) 
ActiveSketch.addConstraint(Sketcher.Constraint('Coincident',30,1,1,1)) 
ActiveSketch.addConstraint(Sketcher.Constraint('Coincident',27,2,17,1)) 
ActiveSketch.addConstraint(Sketcher.Constraint('Coincident',26,1,29,2)) 
ActiveSketch.addConstraint(Sketcher.Constraint('Coincident',30,3,26,1)) 
ActiveSketch.addConstraint(Sketcher.Constraint('Coincident',26,1,0,1)) 
ActiveSketch.addConstraint(Sketcher.Constraint('Coincident',15,1,24,2)) 
ActiveSketch.addGeometry(Part.LineSegment(App.Vector(0.333119,0.799516,0),App.Vector(0.327038,3.175000,0)),True)
ActiveSketch.addConstraint(Sketcher.Constraint('Coincident',31,1,5,1)) 
ActiveSketch.addConstraint(Sketcher.Constraint('Coincident',31,2,3,1)) 
ActiveSketch.addConstraint(Sketcher.Constraint('Vertical',31)) 
ActiveSketch.addGeometry(Part.LineSegment(App.Vector(0.333119,3.175000,0),App.Vector(-0.139372,3.334008,0)),True)
ActiveSketch.addConstraint(Sketcher.Constraint('Coincident',32,1,3,1)) 
ActiveSketch.addConstraint(Sketcher.Constraint('Coincident',32,2,18,1)) 
ActiveSketch.addGeometry(Part.LineSegment(App.Vector(-0.139372,3.334008,0),App.Vector(-0.335875,3.175000,0)),True)
ActiveSketch.addConstraint(Sketcher.Constraint('Coincident',33,1,18,1)) 
ActiveSketch.addConstraint(Sketcher.Constraint('Coincident',33,2,4,1)) 
ActiveSketch.addGeometry(Part.LineSegment(App.Vector(-0.335875,3.175000,0),App.Vector(0.333119,0.799516,0)),True)
ActiveSketch.addConstraint(Sketcher.Constraint('Coincident',34,1,4,1)) 
ActiveSketch.addConstraint(Sketcher.Constraint('Coincident',34,2,5,1)) 
ActiveSketch.addConstraint(Sketcher.Constraint('Perpendicular',32,31)) 
ActiveSketch.addConstraint(Sketcher.Constraint('Perpendicular',34,33)) 
ActiveSketch.addGeometry(Part.ArcOfCircle(Part.Circle(App.Vector(0.325933,0.801433,0),App.Vector(0,0,1),2.429033),1.567838,1.846727),True)
ActiveSketch.addConstraint(Sketcher.Constraint('Coincident',35,3,5,1)) 
ActiveSketch.addConstraint(Sketcher.Constraint('Coincident',35,1,3,1)) 
ActiveSketch.addConstraint(Sketcher.Constraint('Coincident',35,2,4,1)) 
ActiveSketch.addGeometry(Part.LineSegment(App.Vector(-7.163873,-1.587500,0),App.Vector(-7.937500,0.438483,0)),True)
ActiveSketch.addConstraint(Sketcher.Constraint('Coincident',36,1,8,1)) 
ActiveSketch.addConstraint(Sketcher.Constraint('Coincident',36,2,6,1)) 
ActiveSketch.addGeometry(Part.LineSegment(App.Vector(-7.937500,0.438483,0),App.Vector(-9.709600,0.244311,0)),True)
ActiveSketch.addConstraint(Sketcher.Constraint('Coincident',37,1,6,1)) 
ActiveSketch.addConstraint(Sketcher.Constraint('Coincident',37,2,19,1)) 
ActiveSketch.addGeometry(Part.LineSegment(App.Vector(-9.709600,0.244311,0),App.Vector(-9.525000,-1.587500,0)),True)
ActiveSketch.addConstraint(Sketcher.Constraint('Coincident',38,1,19,1)) 
ActiveSketch.addConstraint(Sketcher.Constraint('Coincident',38,2,7,1)) 
ActiveSketch.addGeometry(Part.LineSegment(App.Vector(-9.525000,-1.587500,0),App.Vector(-7.163873,-1.587500,0)),True)
ActiveSketch.addConstraint(Sketcher.Constraint('Coincident',39,1,7,1)) 
ActiveSketch.addConstraint(Sketcher.Constraint('Coincident',39,2,8,1)) 
ActiveSketch.addConstraint(Sketcher.Constraint('Horizontal',39)) 
ActiveSketch.addConstraint(Sketcher.Constraint('Perpendicular',37,36)) 
ActiveSketch.addConstraint(Sketcher.Constraint('Perpendicular',39,38)) 
ActiveSketch.addGeometry(Part.ArcOfCircle(Part.Circle(App.Vector(-7.216743,-1.592726,0),App.Vector(0,0,1),2.394601),1.864784,3.141593),True)
ActiveSketch.addConstraint(Sketcher.Constraint('Coincident',40,3,8,1)) 
ActiveSketch.addConstraint(Sketcher.Constraint('Coincident',40,1,6,1)) 
ActiveSketch.addConstraint(Sketcher.Constraint('Coincident',40,2,7,1)) 
ActiveSketch.addGeometry(Part.LineSegment(App.Vector(-7.229270,-23.185396,0),App.Vector(-9.525000,-23.085960,0)),True)
ActiveSketch.addConstraint(Sketcher.Constraint('Coincident',41,1,9,1)) 
ActiveSketch.addConstraint(Sketcher.Constraint('Coincident',41,2,10,1)) 
ActiveSketch.addConstraint(Sketcher.Constraint('Horizontal',41)) 
ActiveSketch.addGeometry(Part.LineSegment(App.Vector(-9.525000,-23.185398,0),App.Vector(-9.025076,-25.934202,0)),True)
ActiveSketch.addConstraint(Sketcher.Constraint('Coincident',42,1,10,1)) 
ActiveSketch.addConstraint(Sketcher.Constraint('Coincident',42,2,20,1)) 
ActiveSketch.addGeometry(Part.LineSegment(App.Vector(-9.025076,-25.934206,0),App.Vector(-6.318978,-25.517879,0)),True)
ActiveSketch.addConstraint(Sketcher.Constraint('Coincident',43,1,20,1)) 
ActiveSketch.addConstraint(Sketcher.Constraint('Coincident',43,2,11,1)) 
ActiveSketch.addGeometry(Part.LineSegment(App.Vector(-6.318978,-25.559511,0),App.Vector(-7.229270,-23.185400,0)),True)
ActiveSketch.addConstraint(Sketcher.Constraint('Coincident',44,1,11,1)) 
ActiveSketch.addConstraint(Sketcher.Constraint('Coincident',44,2,9,1)) 
ActiveSketch.addConstraint(Sketcher.Constraint('Perpendicular',42,41)) 
ActiveSketch.addConstraint(Sketcher.Constraint('Perpendicular',44,43)) 
ActiveSketch.addGeometry(Part.ArcOfCircle(Part.Circle(App.Vector(-7.183267,-23.176697,0),App.Vector(0,0,1),1.896476),3.141593,4.909330),True)
ActiveSketch.addConstraint(Sketcher.Constraint('Coincident',45,3,9,1)) 
ActiveSketch.addConstraint(Sketcher.Constraint('Coincident',45,1,10,1)) 
ActiveSketch.addConstraint(Sketcher.Constraint('Coincident',45,2,11,1)) 
ActiveSketch.addConstraint(Sketcher.Constraint('Diameter',30,4.638936)) 
ActiveSketch.addConstraint(Sketcher.Constraint('Equal',30,35)) 
ActiveSketch.addConstraint(Sketcher.Constraint('Equal',30,40)) 
ActiveSketch.addConstraint(Sketcher.Constraint('Equal',30,45)) 
ActiveSketch.setDatum(69,App.Units.Quantity('4.622800 mm'))
# Macro End: /home/amcintosh/Documents/FreeCAD/Busybox/Macro/aa_temp_04.FCMacro +++++++++++++++++++++++++++++++++++++++++++++++++
