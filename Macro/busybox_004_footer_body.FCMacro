#  --------------------------------------------------------
#  -- Copyright (c) 2020-06-24 by Aubrey McIntosh, PhD   --
#  -- Permission granted for use in educational settings --
#  -- and personal study with this notice left intact.   --
#  --------------------------------------------------------

# -*- coding: utf-8 -*-

# Macro Begin: /home/amcintosh/.FreeCAD/Macro/shelves_ver_10_5_footer.FCMacro +++++++++++++++++++++++++++++++++++++++++++++++++
import FreeCAD
import PartDesign
import PartDesignGui
import Sketcher

Gui.ActiveDocument.ActiveView.setCamera("#Inventor V2.1 ascii\n\n\nOrthographicCamera {\n  viewportMapping ADJUST_CAMERA\n  position 1024.5903 -1290.296 1165.134\n  orientation 0.82849485 0.2586773 0.49667153  1.1214463\n  nearDistance 195.85522\n  farDistance 2455.8027\n  aspectRatio 1\n  focalDistance 1343.21\n  height 243.7066\n\n}\n")
FreeCAD.Console.PrintMessage("Starting busybox_004_footer.\n")
part_bodies = App.ActiveDocument.addObject('App::Part', 'prototypes_of_bodies_' + str(1))
this_body = part_bodies.newObject("PartDesign::Body","bd_footer_00" + str(1))

this_pad = this_body.newObject("PartDesign::Pad","pd_footer_00" + str(1))
aux_sketch = App.ActiveDocument.copyObject(App.ActiveDocument.sk_footer_000)
Gui.activeDocument().hide(App.ActiveDocument.sk_footer_000.Name)
Gui.activeDocument().hide(aux_sketch.Name)
this_body.Group += [aux_sketch ,]
this_pad.Profile = aux_sketch
this_pad.Length = 10.0
this_pad.setExpression('Length', u'sp_footer.length')
this_pad.Length2 = 99.999800
this_pad.Type = 0
this_pad.UpToFace = None
this_pad.Reversed = 1
this_pad.Midplane = 0
this_pad.Offset = 0.000000
#this_pad.Support = this_body.XZ_Plane, ['']
#this_pad.MapMode = 'FlatFace'
#
#this_pad.setExpression('Placement.Base.z', u'(sp_global.first_shelf_elevation - sp_joist.height - sp_footer.height + sp_footer.notch_depth)')
#
# --------
#
FreeCAD.Console.PrintMessage("Starting busybox_004_footer fencepost.\n")
this_body.newObject("PartDesign::Pad","pd_footer_fencepost_001")
App.activeDocument().pd_footer_fencepost_001.Profile = (App.activeDocument().pd_footer_001, ["Face6"])
App.activeDocument().pd_footer_fencepost_001.Length = 10.0
App.ActiveDocument.pd_footer_fencepost_001.setExpression('Length', u'sp_standard.width')
App.ActiveDocument.pd_footer_fencepost_001.Length2 = 99.999800
App.ActiveDocument.pd_footer_fencepost_001.Type = 0
App.ActiveDocument.pd_footer_fencepost_001.UpToFace = App.activeDocument().pd_footer_001, ["Face6"]
App.ActiveDocument.pd_footer_fencepost_001.Reversed = 0
App.ActiveDocument.pd_footer_fencepost_001.Midplane = 0
App.ActiveDocument.pd_footer_fencepost_001.Offset = 0.000000
#Gui.activeDocument().resetEdit()
Gui.activeDocument().hide("pd_footer_001")
Gui.SendMsgToActiveView("ViewFit")


this_notch = this_body.newObject("PartDesign::Pocket","pk_standard_notch_001")
aux_sketch = App.ActiveDocument.copyObject(App.ActiveDocument.sk_standardF_000)
Gui.activeDocument().hide(aux_sketch.Name)
this_body.Group += [aux_sketch ,]
this_notch.Profile = aux_sketch
this_notch.Length = 5.0
this_notch.Length = 0.000000
this_notch.Length2 = 99.999800
this_notch.Type = 3
this_notch.UpToFace = (App.activeDocument().pd_footer_fencepost_001, ["Face1"])
this_notch.Reversed = 0
this_notch.Midplane = 0
this_notch.setExpression('Offset', u'sp_footer.notch_depth')
#Gui.activeDocument().hide("pd_footer_fencepost_001")
#Gui.activeDocument().resetEdit()
#
# --------  Make the main tenon body
#
this_pad = this_body.newObject("PartDesign::Pad","pd_dowel_001")
stock_sketch = App.ActiveDocument.sk_dowel_000
aux_sketch = App.ActiveDocument.copyObject(stock_sketch)
Gui.activeDocument().hide(stock_sketch.Name)
Gui.activeDocument().hide(aux_sketch.Name)
this_body.Group += [aux_sketch ,]
this_pad.Profile = aux_sketch
this_pad.Type = 3
this_pad.UpToFace = App.activeDocument().pk_standard_notch_001, ["Face1"]
this_pad.Length = 5.0
Gui.activeDocument().hide(aux_sketch.Name)
#
# --------  Trim to fit.  Synthetic chamfer to match drill pocket.
#
this_pocket = this_body.newObject("PartDesign::Pocket","ch_dowel_001")
stock_sketch = App.ActiveDocument.sk_tenon_detail_000
aux_sketch = App.ActiveDocument.copyObject(stock_sketch)
aux_sketch.setExpression('Constraints[0]', u'sp_footer.dowel_dia + 2 thou')
aux_sketch.toggleConstruction(1) 
aux_sketch.toggleConstruction(2) 
aux_sketch.toggleConstruction(6) 
aux_sketch.toggleConstruction(7) 
#
aux_sketch.toggleConstruction(9) 
aux_sketch.toggleConstruction(10) 
aux_sketch.toggleConstruction(11) 
aux_sketch.toggleConstruction(12) 
App.ActiveDocument.recompute()
#

Gui.activeDocument().hide(stock_sketch.Name)
Gui.activeDocument().hide(aux_sketch.Name)
this_body.Group += [aux_sketch ,]
this_pocket.Profile = aux_sketch
this_pocket.Type = 3
this_pocket.UpToFace = this_pad, ["Face13"]
this_pocket.Length = 5.0
Gui.activeDocument().hide(aux_sketch.Name)
App.ActiveDocument.recompute()
#

this_linearpattern = this_body.newObject("PartDesign::LinearPattern","lp_footer_001")
#this_linearpattern.Originals = [this_notch, this_pad,]
this_linearpattern.Originals = [this_notch, this_pad, this_pocket,]
this_linearpattern.Direction = (App.activeDocument().sk_dowel_001, ["V_Axis"])
this_linearpattern.Length = 457.2
this_linearpattern.setExpression('Length', u'sp_footer.length')
this_linearpattern.setExpression('Occurrences', u'sp_global.standard_count')
this_linearpattern.setExpression('Length', u'sp_footer.length')
this_linearpattern.Reversed = 0
this_body.Tip = this_linearpattern
Gui.activeDocument().hide("sk_tenon_detail_000")
Gui.activeDocument().show(this_linearpattern.Name)
Gui.ActiveDocument.getObject(this_linearpattern.Name).Transparency = 50
# Macro End: /home/amcintosh/.FreeCAD/Macro/shelves_footer_linear.FCMacro +++++++++++++++++++++++++++++++++++++++++++++++++
# Macro End: /home/amcintosh/.FreeCAD/Macro/footer_notches.FCMacro +++++++++++++++++++++++++++++++++++++++++++++++++
# Macro End: /home/amcintosh/.FreeCAD/Macro/shelves_ver_10_5_footer.FCMacro +++++++++++++++++++++++++++++++++++++++++++++++++
