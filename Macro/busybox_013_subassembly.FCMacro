#
#  ----
#
this_total_assembly = App.activeDocument().addObject('App::Part','Total_assembly')
this_total_assembly.Group += [
    App.activeDocument().Wall_assembly, \
    App.activeDocument().Shelf_assembly, \
    App.activeDocument().Support_assembly, \
    ]
    
#this_total_assembly = App.ActiveDocument.Total_assembly.Group
