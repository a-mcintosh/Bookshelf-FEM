# -*- coding: utf-8 -*-

# Macro Begin: /home/amcintosh/.FreeCAD/Macro/shelves_009_joist_addendum.FCMacro +++++++++++++++++++++++++++++++++++++++++++++++++

FreeCAD.Console.PrintMessage("Starting busybox_007_joist.\n")
part_bodies = App.ActiveDocument.prototypes_of_bodies_1
this_body = part_bodies.newObject("PartDesign::Body","bd_joist_00" + str(1))

for i in [App.ActiveDocument.sk_joist_000, App.ActiveDocument.sk_spacer_notch_000, \
  App.ActiveDocument.sk_support_000, App.ActiveDocument.sk_support_000, ]:
 aux_sketch = App.ActiveDocument.copyObject(i)
 this_body.Group += [aux_sketch ,]
 Gui.activeDocument().hide(i.Name)
 Gui.activeDocument().hide(aux_sketch.Name)

#
# ----
#
this_sketch = App.ActiveDocument.sk_joist_001
this_pad = this_body.newObject("PartDesign::Pad","pd_joist_")
this_pad.Profile = this_sketch
#this_body_.Length = 10.0
this_pad.setExpression('Length', u'sp_joist.length+sp_spacer.width')
Gui.activeDocument().hide(this_pad.Name)
aux_pad = this_pad

this_pad = this_body.newObject("PartDesign::Pad","pd_joist_fencepost_006")
App.activeDocument().pd_joist_fencepost_006.Profile = (aux_pad, ["Face6"])
#App.activeDocument().pd_joist_fencepost_006.Length = 10
App.activeDocument().pd_joist_fencepost_006.setExpression('Length', u'sp_standard.length')
App.ActiveDocument.pd_joist_fencepost_006.Reversed = 0
Gui.activeDocument().hide(this_pad.Name)
aux_pad = this_pad

this_pad = this_body.newObject("PartDesign::Pad","pd_joist_fencepost_004")
this_pad.Profile = (App.activeDocument().pd_joist_fencepost_006, ["Face4"])
this_pad.setExpression('Length', u'sp_standard.length')
this_pad.Reversed = 0
this_pad.Length2 = 99.999800
this_pad.Type = 0
this_pad.UpToFace = None
this_pad.Midplane = 0
this_pad.Offset = 0.000000
Gui.activeDocument().hide(this_pad.Name)
#Gui.activeDocument().hide(this_body.Name)

# Macro End: /home/amcintosh/.FreeCAD/Macro/shelves_009_joist_addendum.FCMacro +++++++++++++++++++++++++++++++++++++++++++++++++
# --------
# Macro End: /home/amcintosh/.FreeCAD/Macro/shelves_009_joist_addendum.FCMacro +++++++++++++++++++++++++++++++++++++++++++++++++
#
this_pocket = this_body.newObject("PartDesign::Pocket","pk_support_001")
this_sketch = App.ActiveDocument.sk_support_003
this_pocket.Profile = this_sketch
this_pocket.Length = 5.0
this_pocket.Length = 5.003800
this_pocket.Length2 = 99.999800
this_pocket.Type = 1
this_pocket.UpToFace = None
this_pocket.Reversed = 0
this_pocket.Midplane = 0
this_pocket.Offset = 0.000000

Gui.activeDocument().hide(this_pocket.Name)
Gui.activeDocument().hide(this_sketch.Name)
#

App.ActiveDocument.recompute()	# -- workaround line
this_obj_9 = App.ActiveDocument.sk_support_004
this_obj_9.setExpression('Placement.Base.x', u'sp_joist.length+sp_spacer.width')

this_rot = App.Rotation(App.Vector(0, 0, 1), 180)
this_obj_9.Placement.Rotation = this_rot.multiply(this_obj_9.Placement.Rotation)

this_support_pocket = this_body.newObject("PartDesign::Pocket","pk_support_002")
this_support_pocket.Profile = this_obj_9
this_support_pocket.Length = 5.0
App.ActiveDocument.pk_support_002.Length = 5.003800
App.ActiveDocument.pk_support_002.Length2 = 99.999800
App.ActiveDocument.pk_support_002.Type = 'ThroughAll'
App.ActiveDocument.pk_support_002.UpToFace = None
App.ActiveDocument.pk_support_002.Reversed = 1
App.ActiveDocument.pk_support_002.Midplane = 0
App.ActiveDocument.pk_support_002.Offset = 0.000000

Gui.activeDocument().hide(this_obj_9.Name)

# -*- coding: utf-8 -*-

# Macro Begin: /home/amcintosh/.FreeCAD/Macro/shelves_009_joist_spacer.FCMacro +++++++++++++++++++++++++++++++++++++++++++++++++
import FreeCAD
import Sketcher

FreeCAD.Console.PrintMessage("busybox_007_joist, line 84\n")
App.activeDocument().sk_spacer_notch_001.Placement = App.Placement(App.Vector(0.000000,0.000000,25.4*1.250000),App.Rotation(0.000000,0.000000,0.000000,1.000000))
App.activeDocument().sk_spacer_notch_001.MapMode = "Deactivated"
#
this_pocket = this_body.newObject("PartDesign::Pocket","pk_notch_for_spacer")
this_sketch = App.activeDocument().sk_spacer_notch_001
App.activeDocument().pk_notch_for_spacer.Profile = this_sketch
App.activeDocument().pk_notch_for_spacer.Length = 5.0
Gui.activeDocument().hide(this_sketch.Name)
App.ActiveDocument.pk_notch_for_spacer.Length = 0.000000
App.ActiveDocument.pk_notch_for_spacer.Length2 = 99.999800
App.ActiveDocument.pk_notch_for_spacer.Type = 'ThroughAll'
App.ActiveDocument.pk_notch_for_spacer.UpToFace = (App.activeDocument().pk_support_002, ["Face8"])
App.ActiveDocument.pk_notch_for_spacer.Reversed = 1
App.ActiveDocument.pk_notch_for_spacer.Midplane = 0
App.ActiveDocument.pk_notch_for_spacer.Offset = -50.800000
Gui.activeDocument().hide("pk_support_002")
Gui.activeDocument().hide("sk_spacer_notch_001")
#Gui.activeDocument().resetEdit()
Gui.activeDocument().hide(this_pocket.Name)

# Macro End: /home/amcintosh/.FreeCAD/Macro/shelves_009_joist_spacer.FCMacro +++++++++++++++++++++++++++++++++++++++++++++++++

# -*- coding: utf-8 -*-

# Macro Begin: /home/amcintosh/.FreeCAD/Macro/shelves_footer_linear.FCMacro +++++++++++++++++++++++++++++++++++++++++++++++++

this_lp = this_body.newObject("PartDesign::LinearPattern","lp_notch_for_spacer")
this_lp.Originals = [App.activeDocument().pk_notch_for_spacer,]
this_lp.Direction = (App.activeDocument().sk_spacer_notch_001, ["H_Axis"])
this_lp.setExpression('Length', u'sp_joist.length')
this_lp.setExpression('Occurrences', u'sp_joist.spacer_count')
this_lp.Reversed = 0
this_body.Tip = this_lp
Gui.activeDocument().show(this_lp.Name)
Gui.activeDocument().hide("pk_notch_for_spacer")

#Gui.activeDocument().resetEdit()
# Macro End: /home/amcintosh/.FreeCAD/Macro/shelves_bd_joist_linear.FCMacro +++++++++++++++++++++++++++++++++++++++++++++++++
