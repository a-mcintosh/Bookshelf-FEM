#  --------------------------------------------------------
#  -- Copyright (c) 2020-06-24 by Aubrey McIntosh, PhD   --
#  -- Permission granted for use in educational settings --
#  -- and personal study with this notice left intact.   --
#  --------------------------------------------------------

# -*- coding: utf-8 -*-

# Macro Begin: /home/amcintosh/.FreeCAD/Macro/shelves_009_skirt_addendum.FCMacro +++++++++++++++++++++++++++++++++++++++++++++++++

FreeCAD.Console.PrintMessage("Starting busybox_007_skirt.\n")
part_bodies = App.ActiveDocument.prototypes_of_bodies_1
this_body = part_bodies.newObject("PartDesign::Body","bd_skirt_00" + str(1))

for i in [App.ActiveDocument.sk_joist_000, App.ActiveDocument.sk_spacer_body_000, \
  App.ActiveDocument.sk_support_000, App.ActiveDocument.sk_support_000, \
  App.ActiveDocument.sk_dovetail_top_000, \
  App.ActiveDocument.sk_skirt_path_000, ]:
 aux_sketch = App.ActiveDocument.copyObject(i)
 this_body.Group += [aux_sketch ,]
 Gui.activeDocument().hide(i.Name)
 FreeCAD.Console.PrintMessage("\tNew sketch name: " + aux_sketch.Name + "\n")

#
# ----
#
this_sketch = App.ActiveDocument.sk_joist_002
this_sketch.setExpression('Placement.Base.y', u'-sp_joist.width')
this_pad = this_body.newObject("PartDesign::Pad","pd_skirt_")
this_pad.Profile = this_sketch
#this_body_.Length = 10.0
this_pad.setExpression('Length', u'sp_joist.length+sp_spacer.width')
Gui.activeDocument().hide(this_pad.Name)
Gui.activeDocument().hide(this_sketch.Name)
aux_pad = this_pad

this_pocket = this_body.newObject("PartDesign::Pocket","pk_support_006")
this_sketch = App.ActiveDocument.sk_support_006
this_pocket.Profile = this_sketch
this_pocket.Length = 5.0
this_pocket.Length = 5.003800
this_pocket.Length2 = 99.999800
this_pocket.setExpression('Length', u'sp_standard.width')
this_pocket.Length2 = 99.999800
this_pocket.Type = 0
this_pocket.UpToFace = None
this_pocket.Reversed = 0
this_pocket.Midplane = 0
this_pocket.Offset = 0.000000

App.ActiveDocument.recompute()	# -- workaround line
this_obj_9 = App.ActiveDocument.sk_support_007
this_obj_9.setExpression('Placement.Base.x', u'sp_joist.length+sp_spacer.width')

this_rot = App.Rotation(App.Vector(0, 0, 1), 180)
this_obj_9.Placement.Rotation = this_rot.multiply(this_obj_9.Placement.Rotation)

this_support_pocket = this_body.newObject("PartDesign::Pocket","pk_support_007")
this_support_pocket.Profile = this_obj_9
this_support_pocket.Length = 5.0
this_support_pocket.Length = 5.003800
this_support_pocket.Length2 = 99.999800
this_support_pocket.Type = 'ThroughAll'
this_support_pocket.UpToFace = None
this_support_pocket.Reversed = 1
this_support_pocket.Midplane = 0
this_support_pocket.Offset = 0.000000

Gui.activeDocument().hide(this_obj_9.Name)
#App.activeDocument().sk_spacer_notch_002.MapMode = "Deactivated"
#
this_plane = App.activeDocument().bd_skirt_001.newObject('PartDesign::Plane','DatumPlane')
this_sketch = App.ActiveDocument.copyObject(App.ActiveDocument.sk_skirt_path_000)
this_body.Group += [this_sketch, ]
this_plane.Support = [(this_sketch,'Edge1')]
this_plane.MapMode = 'NormalToEdge'
App.ActiveDocument.DatumPlane.AttachmentOffset = App.Placement(App.Vector(-19.0500000000, 0.0000000000, 0.0000000000),  App.Rotation(0.0000000000, 0.0000000000, 0.0000000000))
#
#  --  sk_spacer_notchH_001
#
this_sketch = App.ActiveDocument.copyObject(App.ActiveDocument.sk_spacer_notchH_000)
this_body.Group += [this_sketch, ]
this_sketch.Support = (this_plane, [''])
this_sketch.MapMode = 'FlatFace'
this_sketch.setExpression('Constraints[13]', u'0')
FreeCAD.Console.PrintMessage("Placement for sketch " + this_sketch.Name + " " + str(this_sketch.Placement) + "\n")
#
#  --  SubtractivePipe
#
this_pipe = App.activeDocument().bd_skirt_001.newObject("PartDesign::SubtractivePipe","SubtractivePipe")
this_body.Group += [this_sketch,]
this_pipe.Profile = this_sketch
aux_sketch = App.ActiveDocument.copyObject(App.ActiveDocument.sk_skirt_path_000)
this_body.Group += [aux_sketch, ]
this_pipe.Spine = aux_sketch
Gui.activeDocument().hide(this_plane.Name)
Gui.activeDocument().hide(App.ActiveDocument.sk_skirt_path_001.Name)
#
#
#
this_lp = this_body.newObject("PartDesign::LinearPattern","lp_notch_for_spacer_002")
this_lp.Originals = [App.activeDocument().SubtractivePipe,]
this_lp.Direction = (App.activeDocument().sk_spacer_body_001, ["H_Axis"])
this_lp.setExpression('Length', u'sp_joist.length')
this_lp.setExpression('Occurrences', u'sp_joist.spacer_count')
this_lp.Reversed = 0
this_body.Tip = this_lp
Gui.ActiveDocument.getObject(this_lp.Name).Transparency=25
Gui.activeDocument().show(this_lp.Name)
App.ActiveDocument.recompute()
#Gui.activeDocument().resetEdit()
# Macro End: /home/amcintosh/.FreeCAD/Macro/shelves_bd_skirt_linear.FCMacro +++++++++++++++++++++++++++++++++++++++++++++++++
