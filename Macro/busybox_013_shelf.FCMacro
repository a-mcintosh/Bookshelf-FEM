#  --------------------------------------------------------
#  -- Copyright (c) 2020-06-24 by Aubrey McIntosh, PhD   --
#  -- Permission granted for use in educational settings --
#  -- and personal study with this notice left intact.   --
#  --------------------------------------------------------

# -*- coding: utf-8 -*-

# Macro Begin: /home/amcintosh/Documents/FreeCAD/Busybox/Macro/busybox_shelf.FCMacro +++++++++++++++++++++++++++++++++++++++++++++++++
import FreeCAD
import shelf_nr

#
#shelf_nr = int(App.ActiveDocument.sp_global.get(App.ActiveDocument.sp_global.getCellFromAlias("shelf_nr")))
height1 = float(App.ActiveDocument.sp_standard.get(App.ActiveDocument.sp_standard.getCellFromAlias("item_height")))
height2 = float(App.ActiveDocument.sp_joist.get(App.ActiveDocument.sp_joist.getCellFromAlias("height")))
FreeCAD.Console.PrintMessage(" busybox_012_shelf. shelf_nr_value " + str(shelf_nr.get_shelf_nr()) + "\n")
#
this_part_shelf = App.activeDocument().addObject('App::Part','Shelf_')
this_part_shelf.Placement.Base.z = shelf_nr.get_shelf_nr()*(height1 + height2)
this_assembly = App.activeDocument().Shelf_assembly
this_assembly.Group += [this_part_shelf, ]

joist_staging_shelf = App.activeDocument().addObject('App::Part','explode_joist_00' + str(shelf_nr.get_shelf_nr()))
spacer_staging_shelf = App.activeDocument().addObject('App::Part','explode_spacer_00' + str(shelf_nr.get_shelf_nr()))
skirt_staging_shelf = App.activeDocument().addObject('App::Part','explode_skirt_00' + str(shelf_nr.get_shelf_nr()))

this_part_shelf.Group += [ \
  joist_staging_shelf, spacer_staging_shelf, skirt_staging_shelf,
  ]
  
ix = 0
for i in [ \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  App.ActiveDocument.lp_notch_for_spacer,  \
  ]:
 aux_body = App.ActiveDocument.copyObject(i)
 Gui.activeDocument().show(aux_body.Name)
 aux_part = App.activeDocument().addObject('PartDesign::Body','bd_joist_00'+str(2+ix))
 aux_part.Placement.Base.y = 25.4 * (ix * 2 + (ix%2 * 0.5))
 aux_part.Group += [aux_body ,]
 joist_staging_shelf.Group += [aux_part ,]
 ix += 1

ix = 0
for i in [ \
  App.ActiveDocument.sup_spacer_skirt_notch_002,  \
  App.ActiveDocument.sup_spacer_skirt_notch_002,  \
  App.ActiveDocument.sup_spacer_skirt_notch_002,  \
  App.ActiveDocument.sup_spacer_skirt_notch_002,  \
  App.ActiveDocument.sup_spacer_skirt_notch_002,  \
  App.ActiveDocument.sup_spacer_skirt_notch_002,  \
  App.ActiveDocument.sup_spacer_skirt_notch_002,  \
  App.ActiveDocument.sup_spacer_skirt_notch_002,  \
  App.ActiveDocument.sup_spacer_skirt_notch_002,  \
  ]:
 aux_body = App.ActiveDocument.copyObject(i)
 Gui.activeDocument().show(aux_body.Name)
 aux_part = App.activeDocument().addObject('PartDesign::Body','bd_spacer_00'+str(2+ix))
 aux_part.Placement.Base.x = ix * 25.4 * 6
 aux_part.Group += [aux_body ,]
 spacer_staging_shelf.Group += [aux_part ,]
 ix += 1

ix = 0
for i in [ \
  App.ActiveDocument.lp_notch_for_spacer_002,  \
  App.ActiveDocument.lp_notch_for_spacer_002,  \
  ]:
 aux_body = App.ActiveDocument.copyObject(i)
 aux_part = App.activeDocument().addObject('PartDesign::Body','bd_skirt_00'+str(2+ix))
 this_y = float(App.ActiveDocument.sp_footer.get(App.ActiveDocument.sp_footer.getCellFromAlias("length"))) \
   + 0*float(App.ActiveDocument.sp_joist.get(App.ActiveDocument.sp_joist.getCellFromAlias("width")))
 aux_part.Placement.Base.y = ix * this_y
 aux_part.Group += [aux_body ,]
 skirt_staging_shelf.Group += [aux_part ,]
 Gui.activeDocument().show(aux_body.Name)
 ix += 1

#  ----
this_part_support = App.activeDocument().addObject('App::Part','Support_')
this_part_support.Placement.Base.z = shelf_nr.get_shelf_nr()*(height1 + height2)
ix = 0
for i in [ \
  App.ActiveDocument.pd_support,  \
  App.ActiveDocument.pd_support,  \
  ]:
 aux_body = App.ActiveDocument.copyObject(i)
 aux_part = App.activeDocument().addObject('PartDesign::Body','bd_support_00'+str(2+ix))
 aux_part.Placement.Base.y += ix * 25.4 * 24
 aux_part.Group += [aux_body ,]
 this_part_support.Group += [aux_part ,]
 ix += 1

this_support_assembly = App.activeDocument().Support_assembly
this_support_assembly.Group += [this_part_support, ]
FreeCAD.Console.PrintMessage(" busybox_012_shelf. 80\n")

aux_part.setExpression('Placement.Base.x', u'sp_joist.length+sp_spacer.width')
aux_part.setExpression('Placement.Base.y', u'sp_footer.length+sp_joist.width')
this_rot = App.Rotation(App.Vector(0, 0, 1), 180)
aux_part.Placement.Rotation = this_rot.multiply(aux_part.Placement.Rotation)

#The set stataement, following, produces errors.  As a workaround, set shelf_nr.get_shelf_nr()=... from the console.
#App.ActiveDocument.sp_global.set(App.ActiveDocument.sp_global.getCellFromAlias("shelf_nr.get_shelf_nr()"), str(int(shelf_nr.get_shelf_nr()+1)))

shelf_nr.set_shelf_nr(shelf_nr.get_shelf_nr()+1)

# Macro End: /home/amcintosh/Documents/FreeCAD/Busybox/Macro/busybox_shelf.FCMacro +++++++++++++++++++++++++++++++++++++++++++++++++
