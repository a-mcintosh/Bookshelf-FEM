# -*- coding: utf-8 -*-

# Macro Begin: /home/amcintosh/Documents/FreeCAD/Busybox/Macro/aa_temp_05.FCMacro +++++++++++++++++++++++++++++++++++++++++++++++++
import FreeCAD
import Sketcher

ActiveSketch.addGeometry(Part.LineSegment(App.Vector(19.121969,3.037695,0),App.Vector(0.318893,3.170556,0)),True)
ActiveSketch.addConstraint(Sketcher.Constraint('Coincident',46,1,2,1)) 
ActiveSketch.addConstraint(Sketcher.Constraint('Coincident',46,2,3,1)) 
ActiveSketch.addConstraint(Sketcher.Constraint('Horizontal',46)) 
ActiveSketch.addConstraint(Sketcher.Constraint('Perpendicular',46,29)) 
#ActiveSketch.addConstraint(Sketcher.Constraint('Perpendicular',31,46)) 
ActiveSketch.addGeometry(Part.LineSegment(App.Vector(-0.328835,3.123365,0),App.Vector(-7.903853,0.708426,0)),True)
ActiveSketch.addConstraint(Sketcher.Constraint('Coincident',47,1,4,1)) 
ActiveSketch.addConstraint(Sketcher.Constraint('Coincident',47,2,6,1)) 
ActiveSketch.addConstraint(Sketcher.Constraint('Perpendicular',47,34)) 
ActiveSketch.addConstraint(Sketcher.Constraint('Perpendicular',36,36)) 
ActiveSketch.addConstraint(Sketcher.Constraint('Perpendicular',36,47)) 
#ActiveSketch.addConstraint(Sketcher.Constraint('Perpendicular',36,47)) 
ActiveSketch.delConstraint(80)
ActiveSketch.addGeometry(Part.LineSegment(App.Vector(-9.567698,-1.495648,0),App.Vector(-9.387992,-23.421175,0)),True)
ActiveSketch.addConstraint(Sketcher.Constraint('Coincident',48,1,7,1)) 
ActiveSketch.addConstraint(Sketcher.Constraint('Coincident',48,2,10,1)) 
ActiveSketch.addConstraint(Sketcher.Constraint('Vertical',48)) 
#ActiveSketch.addConstraint(Sketcher.Constraint('Perpendicular',48,39)) 
#ActiveSketch.addConstraint(Sketcher.Constraint('Perpendicular',41,48)) 
ActiveSketch.addGeometry(Part.LineSegment(App.Vector(-6.876204,-25.764820,0),App.Vector(0.241498,-23.188477,0)),True)
ActiveSketch.addConstraint(Sketcher.Constraint('Coincident',49,1,11,1)) 
ActiveSketch.addConstraint(Sketcher.Constraint('Coincident',49,2,12,1)) 
ActiveSketch.addConstraint(Sketcher.Constraint('Perpendicular',49,44)) 
ActiveSketch.addConstraint(Sketcher.Constraint('Parallel',47,49)) 
ActiveSketch.addGeometry(Part.LineSegment(App.Vector(0.240140,-23.189465,0),App.Vector(23.209347,-0.000000,0)),True)
ActiveSketch.addConstraint(Sketcher.Constraint('Coincident',50,1,12,1)) 
ActiveSketch.addConstraint(Sketcher.Constraint('Coincident',50,2,16,1)) 
ActiveSketch.addGeometry(Part.LineSegment(App.Vector(23.209347,-0.000000,0),App.Vector(20.828791,2.430168,0)),True)
ActiveSketch.addConstraint(Sketcher.Constraint('Coincident',51,1,16,1)) 
ActiveSketch.addConstraint(Sketcher.Constraint('Coincident',51,2,1,1)) 
ActiveSketch.addConstraint(Sketcher.Constraint('Perpendicular',51,50)) 
ActiveSketch.addConstraint(Sketcher.Constraint('Perpendicular',26,51)) 
# Macro End: /home/amcintosh/Documents/FreeCAD/Busybox/Macro/aa_temp_05.FCMacro +++++++++++++++++++++++++++++++++++++++++++++++++
