# -*- coding: utf-8 -*-

# Macro Begin: /home/amcintosh/.FreeCAD/Macro/shelves_007_support_base_addendum.FCMacro +++++++++++++++++++++++++++++++++++++++++++++++++

FreeCAD.Console.PrintMessage("Starting busybox_006_support.\n")
part_bodies = App.ActiveDocument.prototypes_of_bodies_1
this_part = App.ActiveDocument.addObject('App::Part', 'pt_support_00' + str(1))
part_bodies.Group += [this_part, ]
this_body = part_bodies.newObject("PartDesign::Body","bd_support_" + str(1))
this_part.addObject(this_body)

for i in [ \
   App.ActiveDocument.sk_support_000,]:
 aux_sketch = App.ActiveDocument.copyObject(i)
 this_body.Group += [aux_sketch ,]
 Gui.activeDocument().hide(i.Name)
 Gui.activeDocument().hide(aux_sketch.Name)

#
# ----
#

this_sketch = App.activeDocument().sk_support_002
#this_sketch.Support = (App.activeDocument().XZ_Plane, [''])
this_sketch.MapMode = 'FlatFace'
this_pad = this_body.newObject("PartDesign::Pad","pd_support")
this_pad.Profile = this_sketch
this_pad.Length = 10.0
this_pad.setExpression('Length', u'sp_footer.length + sp_standard.width')
this_pad.Length2 = 99.999800
this_pad.Type = 0
this_pad.UpToFace = None
this_pad.Reversed = 1
this_pad.Midplane = 0
this_pad.Offset = 0.000000

# Macro End: /home/amcintosh/.FreeCAD/Macro/shelves_007_support_body_addendum.FCMacro +++++++++++++++++++++++++++++++++++++++++++++++++
