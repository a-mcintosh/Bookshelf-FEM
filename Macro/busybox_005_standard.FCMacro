#  --------------------------------------------------------
#  -- Copyright (c) 2020-06-24 by Aubrey McIntosh, PhD   --
#  -- Permission granted for use in educational settings --
#  -- and personal study with this notice left intact.   --
#  --------------------------------------------------------

# -*- coding: utf-8 -*-

# Macro Begin: /home/amcintosh/.FreeCAD/Macro/shelves_007_standard_body.FCMacro +++++++++++++++++++++++++++++++++++++++++++++++++
 
FreeCAD.Console.PrintMessage("Starting busybox_005_standard.\n")
part_bodies = App.ActiveDocument.prototypes_of_bodies_1
this_body = part_bodies.newObject("PartDesign::Body","bd_standard_" + str(1))

for i in [App.ActiveDocument.sk_standardF_000, App.ActiveDocument.sk_dowel_000, \
  App.ActiveDocument.sk_dowel_000, App.ActiveDocument.sk_support_000,]:
 aux_sketch = App.ActiveDocument.copyObject(i)
 this_body.Group += [aux_sketch ,]
 Gui.activeDocument().hide(i.Name)
 Gui.activeDocument().hide(aux_sketch.Name)

#
# ----
#
this_pad = this_body.newObject("PartDesign::Pad","pd_standardF_002")
this_pad.Profile = App.ActiveDocument.getObject("sk_standardF_002")
this_pad.Length = 10.0
this_pad.setExpression('Length', u'sp_standard.height')
this_pad.Length2 = 99.999800
this_pad.Type = 0
this_pad.UpToFace = None
this_pad.Reversed = 0
this_pad.Midplane = 0
this_pad.Offset = 0.000000
Gui.activeDocument().hide(this_pad.Name)
#
# ----
#
this_pad_extension = this_body.newObject("PartDesign::Pad","pd_standard_extendF")
this_pad_extension.Profile = App.ActiveDocument.sk_standardF_002
this_pad_extension.Length = 10.0
this_pad_extension.setExpression('Length', u'(sp_global.first_shelf_elevation - sp_joist.height \
  - sp_footer.height + sp_footer.notch_depth)')
this_pad_extension.Length2 = 99.999800
this_pad_extension.Type = 0
this_pad_extension.UpToFace = None
this_pad_extension.Reversed = 1
this_pad_extension.Midplane = 0
this_pad_extension.Offset = 0.000000

#
#  ---- designated location for mortise
#
this_pocket = this_body.newObject("PartDesign::Pocket","ch_mortise_001")
stock_sketch = App.ActiveDocument.sk_tenon_detail_000
this_sketch = App.ActiveDocument.copyObject(stock_sketch)
this_sketch.setExpression('Constraints[0]', u'sp_footer.dowel_dia + 2 thou')
this_sketch.toggleConstruction(4) 
this_sketch.toggleConstruction(5) 
this_sketch.toggleConstruction(12) 
this_sketch.toggleConstruction(14)
this_sketch.toggleConstruction(15)
this_sketch.toggleConstruction(16)
#
Gui.activeDocument().hide(stock_sketch.Name)
Gui.activeDocument().hide(this_sketch.Name)
this_body.Group += [this_sketch ,]
this_pocket.Profile = this_sketch
this_pocket.Type = 3
this_pocket.UpToFace = this_pad_extension, ["Face4"]
this_pocket.Length = 5.0
Gui.activeDocument().hide(this_sketch.Name)
App.ActiveDocument.recompute()
#
# --- This is very handy ---> Gui.Selection.getSelectionEx()[0].SubElementNames
#
# ----
#
FreeCAD.Console.PrintMessage("busybox_005_standard, line 79\n")
FreeCAD.Console.PrintMessage(this_sketch.Name + "--> \n")
this_sketch = App.ActiveDocument.copyObject(this_sketch)
this_body.Group += [this_sketch ,]
FreeCAD.Console.PrintMessage("--> " + this_sketch.Name + "\n")
FreeCAD.Console.PrintMessage("--> " + this_sketch.Label + "\n")

this_sketch.setExpression('Placement.Base.z', u'sp_standard.height')
this_rot = App.Rotation( App.Vector(1, 0, 0), 180).multiply(this_sketch.Placement.Rotation)
this_sketch.Placement.Rotation = this_rot

FreeCAD.Console.PrintMessage("busybox_005_standard, line 86\n")
this_sketch.MapMode = 'FlatFace'
FreeCAD.Console.PrintMessage("busybox_005_standard, line 88\n")
aux_pocket = this_pocket
this_pocket = this_body.newObject("PartDesign::Pocket","pk_mortise_002")
this_pocket.Profile = this_sketch
this_pocket.setExpression('Length', u'sp_footer.dowel_length/2')
this_pocket.Reversed = 1
this_pocket.Type = 'ThroughAll'
#
this_pocket = this_body.newObject("PartDesign::Pocket","pk_support_notch")
this_sketch = App.ActiveDocument.copyObject(App.ActiveDocument.sk_support_000)
this_body.Group += [this_sketch ,]
this_pocket.Profile = this_sketch
this_pocket.Type = 3
this_pocket.Length = 5.0
Gui.activeDocument().hide("sk_support_000")
this_pocket.UpToFace = this_pad_extension, ["Face1"]
this_pocket.Length = 0.000000
this_pocket.Length2 = 99.999800
this_pocket.Type = 'ThroughAll'
this_pocket.Reversed = 0
this_pocket.Midplane = 0
Gui.activeDocument().hide("sk_support_001")
Gui.activeDocument().show(this_pocket.Name)


this_linearpattern = this_body.newObject("PartDesign::LinearPattern","lp_support")
this_linearpattern.Originals = [this_pocket,]
this_linearpattern.Direction = (App.activeDocument().sk_support_001, ["V_Axis"])
#

#
this_linearpattern.setExpression('Length', u'(sp_standard.shelf_count-1)*(sp_standard.item_height+sp_joist.height)')
FreeCAD.Console.PrintMessage("busybox_005_standard, line 140" + "\n")
this_linearpattern.Occurrences = 12
this_linearpattern.setExpression('Occurrences', u'sp_standard.shelf_count')
this_linearpattern.Reversed = 0
this_body.Tip = this_linearpattern
Gui.activeDocument().show(this_linearpattern.Name)
Gui.activeDocument().hide("pk_support_notch")
#Gui.activeDocument().resetEdit()
#
# ----
#
FreeCAD.Console.PrintMessage("busybox_005_standard, line 105\n")
this_ch = this_body.newObject("PartDesign::Chamfer","ch_standard")
this_ch.Base = (this_linearpattern,["Edge54", "Edge60", \
  "Edge42", "Edge48",])
Gui.activeDocument().hide(this_pocket.Name)
this_ch.Size = 1.270000
Gui.activeDocument().hide("pd_standard_extendF")
Gui.activeDocument().show(this_linearpattern.Name)

Gui.activeDocument().resetEdit()
Gui.ActiveDocument.getObject(this_ch.Name).Transparency = 75
App.activeDocument().recompute()
Gui.activeDocument().show(this_ch.Name)
