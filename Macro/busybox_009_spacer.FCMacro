#  --------------------------------------------------------
#  -- Copyright (c) 2020-06-24 by Aubrey McIntosh, PhD   --
#  -- Permission granted for use in educational settings --
#  -- and personal study with this notice left intact.   --
#  --------------------------------------------------------

# -*- coding: utf-8 -*-

# Macro Begin: /home/amcintosh/.FreeCAD/Macro/shelves_010_spacer.FCMacro +++++++++++++++++++++++++++++++++++++++++++++++++
import FreeCAD
import PartDesignGui
import Sketcher

FreeCAD.Console.PrintMessage("Starting busybox_008_spacer.\n")

part_bodies = App.ActiveDocument.prototypes_of_bodies_1
this_body = part_bodies.newObject("PartDesign::Body","bd_spacer_00" + str(1))

for i in [App.ActiveDocument.sk_spacer_body_000, \
  App.ActiveDocument.sk_spacer_notch_000, App.ActiveDocument.sk_spacer_notch_000,  \
  App.ActiveDocument.sk_dovetail_bottom_000, App.ActiveDocument.sk_dovetail_bottom_000, \
  App.ActiveDocument.sk_skirt_path_000, ]:
 aux_sketch = App.ActiveDocument.copyObject(i)
 this_body.Group += [aux_sketch ,]
 Gui.activeDocument().hide(i.Name)
 Gui.activeDocument().hide(aux_sketch.Name)

#
#
# ----
#
#
this_sketch = App.activeDocument().sk_spacer_body_002
this_sketch.MapMode = 'FlatFace'
#
this_pad = this_body.newObject("PartDesign::Pad","pd_spacer")
this_pad.Profile = this_sketch
this_pad.setExpression('Length', u'sp_footer.length + sp_standard.width')
this_pad.Length2 = 99.999800
this_pad.Type = 0
this_pad.UpToFace = None
this_pad.Reversed = 1
this_pad.Midplane = 0
this_pad.Offset = 0.000000
Gui.activeDocument().hide(this_pad.Name)
#
this_plane = this_body.newObject('PartDesign::Plane','DP_notchE')
this_plane.Support = [(App.activeDocument().sk_skirt_path_004,'Edge1')]
this_plane.MapMode = 'NormalToEdge'
aux_placement_y = float(0.0 \
  + float(App.ActiveDocument.sp_joist.get(App.ActiveDocument.sp_joist.getCellFromAlias("height"))) \
  - float(App.ActiveDocument.sp_spacer.get(App.ActiveDocument.sp_spacer.getCellFromAlias("notch_depth"))) )
this_plane.AttachmentOffset = App.Placement(App.Vector(-19.0500000000, -aux_placement_y, 0.0),  App.Rotation(0.0000000000, 0.0000000000, 0.0000000000))
this_plane.MapReversed = False
Gui.activeDocument().hide(this_plane.Name)
#
App.activeDocument().bd_spacer_001.Tip = this_plane
this_sketch = App.ActiveDocument.copyObject(App.ActiveDocument.sk_spacer_notchH_000)
App.activeDocument().bd_spacer_001.addObject(this_sketch)
FreeCAD.Console.PrintMessage("line 60, sketch " + this_sketch.Name + "\n")

#
this_sketch.Support = (this_plane, '')
this_sketch.MapMode = "FlatFace"

this_sketch.toggleConstruction(9) 
this_sketch.toggleConstruction(7) 
this_sketch.toggleConstruction(8) 
this_sketch.toggleConstruction(3) 
this_sketch.toggleConstruction(2) 
this_sketch.toggleConstruction(1) 

App.ActiveDocument.recompute()
FreeCAD.Console.PrintMessage("line 67; The " + this_plane.Name +" placement " + str(this_plane.Placement) + "\n")
this_notch_e = App.activeDocument().bd_spacer_001.newObject("PartDesign::Pocket","pk_spacer_joist_notchE")
Gui.ActiveDocument.getObject(this_notch_e.Name).Transparency=50
this_notch_e.Profile = this_sketch
this_notch_e.Length = 25.4*0.75
this_notch_e.Length2 = 99.999800
this_notch_e.Type = 0
this_notch_e.UpToFace = None
this_notch_e.Reversed = 1
this_notch_e.Midplane = 0
this_notch_e.Offset = 0.000000
FreeCAD.Console.PrintMessage( "line 79\n")
Gui.activeDocument().hide(this_notch_e.Name)
#
this_plane = this_body.newObject('PartDesign::Plane','DatumPlane002')
this_plane.AttachmentOffset = App.Placement(App.Vector(0,0, -25.4 * 3.25),  App.Rotation(0.0000000000, 0.0000000000, 0.0000000000))
this_plane.MapReversed = False
this_plane.Support = [(this_pad,'Face5')]
this_plane.MapMode = 'FlatFace'
Gui.activeDocument().hide(this_plane.Name)
App.ActiveDocument.recompute()
FreeCAD.Console.PrintMessage("line 87; The DatumPlane002 placement " + str(App.activeDocument().DatumPlane002.Placement) + "\n")
#
this_notch_o = this_body.newObject("PartDesign::Pocket","pk_spacer_joist_notchO")
this_sketch = App.ActiveDocument.copyObject(this_sketch)
App.activeDocument().bd_spacer_001.addObject(this_sketch)
this_sketch.Support = (App.activeDocument().DatumPlane002, '')
this_sketch.Placement = this_plane.Placement
App.ActiveDocument.recompute()
FreeCAD.Console.PrintMessage("The sketch placement " + str(this_sketch.Placement) + "\n")

this_notch_o.Profile = this_sketch
this_notch_o.Length = 25.4*0.75
this_notch_o.Length2 = 99.999800
this_notch_o.Type = 0
this_notch_o.Reversed = 0
this_notch_o.Midplane = 0
this_notch_o.Offset = -50.800000
App.ActiveDocument.recompute()
Gui.activeDocument().hide(this_notch_o.Name)
#
# ----  lp_notch_for_joist
#
this_linear = this_body.newObject("PartDesign::LinearPattern","lp_notch_for_joist")
FreeCAD.Console.PrintMessage("Internal name " + this_linear.Name + ".\n")
this_linear.Originals = [this_notch_e, this_notch_o, ]
this_linear.Direction = (App.activeDocument().sk_spacer_notch_002, ["V_Axis"])
this_linear.setExpression('Length', u'sp_footer.length-4 in ')
this_linear.setExpression('Occurrences', u'sp_spacer.spacer_count')
this_linear.Reversed = 0
this_body.Tip = this_linear
Gui.activeDocument().hide(this_linear.Name)
#
#  --  pk_spacer_skirt_notch_001
#
this_plane = App.activeDocument().bd_spacer_001.newObject('PartDesign::Plane','DP_notch_005')
this_path = App.activeDocument().sk_skirt_path_004
this_plane.Support = [(this_path,'Edge1'), (this_path,'Vertex1')]
this_plane.MapMode = 'NormalToEdge'
this_plane.AttachmentOffset = App.Placement(App.Vector(-19.0500000000, -aux_placement_y, 0.0),  App.Rotation(0.0000000000, 0.0000000000, 0.0000000000))
Gui.activeDocument().hide(this_plane.Name)
#
this_sketch = App.ActiveDocument.copyObject(App.ActiveDocument.sk_spacer_notchH_000)
this_sketch.Support = (this_plane, [''])
this_sketch.MapMode = 'FlatFace'
this_sketch.toggleConstruction(9) 
this_sketch.toggleConstruction(7) 
this_sketch.toggleConstruction(8) 
this_sketch.toggleConstruction(3) 
this_sketch.toggleConstruction(2) 
this_sketch.toggleConstruction(1) 
this_body.addObject(this_sketch)
this_sketch.Support = (this_plane, [''])
#
this_pipe = this_body.newObject("PartDesign::SubtractivePipe","sup_spacer_skirt_notch_001")
aux_sketch = App.ActiveDocument.copyObject(App.ActiveDocument.sk_skirt_path_002)
this_body.addObject(aux_sketch)
this_pipe.Profile = this_sketch
this_pipe.Spine = aux_sketch
Gui.ActiveDocument.getObject(this_pipe.Name).Transparency=50
Gui.activeDocument().hide(this_pipe.Name)
App.ActiveDocument.recompute()
#
#  --  pk_spacer_skirt_notch_002
#
this_path = App.ActiveDocument.copyObject(App.activeDocument().sk_skirt_path_000)
this_body.addObject(this_path)
aux_rot = App.Rotation( App.Vector(0, 0, 1), 180)
old_rot = this_path.Placement.Rotation
new_rot = aux_rot.multiply(old_rot)
this_path.Placement.Rotation = new_rot
this_path.Placement.Base.y += float(App.ActiveDocument.sp_footer.get(App.ActiveDocument.sp_footer.getCellFromAlias("length"))) \
  + float(App.ActiveDocument.sp_joist.get(App.ActiveDocument.sp_joist.getCellFromAlias("width")))
this_plane = App.activeDocument().bd_spacer_001.newObject('PartDesign::Plane','DP_notch006')
this_plane.Support = [(this_path,'Edge3'), (this_path,'Vertex3')]
this_plane.MapMode = 'NormalToEdge'
this_plane.AttachmentOffset = App.Placement(App.Vector(0.0, -aux_placement_y, 0.0),  App.Rotation(0.0000000000, 0.0000000000, 0.0000000000))
App.ActiveDocument.recompute()
#
this_sketch = App.ActiveDocument.copyObject(App.ActiveDocument.sk_spacer_notchH_000)
this_sketch.Support = (this_plane, [''])
this_sketch.MapMode = 'FlatFace'
this_sketch.toggleConstruction(9) 
this_sketch.toggleConstruction(7) 
this_sketch.toggleConstruction(8) 
this_sketch.toggleConstruction(3) 
this_sketch.toggleConstruction(2) 
this_sketch.toggleConstruction(1) 
this_body.addObject(this_sketch)
this_sketch.Support = (this_plane, [''])
#
this_pipe = this_body.newObject("PartDesign::SubtractivePipe","sup_spacer_skirt_notch_002")
this_pipe.Profile = this_sketch
this_pipe.Spine = this_path
Gui.ActiveDocument.getObject(this_pipe.Name).Transparency=50
Gui.activeDocument().hide(this_plane.Name)
