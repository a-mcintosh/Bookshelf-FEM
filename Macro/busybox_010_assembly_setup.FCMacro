#  --------------------------------------------------------
#  -- Copyright (c) 2020-06-24 by Aubrey McIntosh, PhD   --
#  -- Permission granted for use in educational settings --
#  -- and personal study with this notice left intact.   --
#  --------------------------------------------------------

import shelf_nr
shelf_nr.set_shelf_nr(0)

FreeCAD.Console.PrintMessage("busybox_010_assembly, line 105; shelf_nr " + str(shelf_nr.get_shelf_nr()) + "\n")
Gui.ActiveDocument.ActiveView.setCamera('#Inventor V2.1 ascii\n\n\nOrthographicCamera {\n  viewportMapping ADJUST_CAMERA\n  position 1321.6816 221.37732 1544.3434\n  orientation 0.89191508 0.26466164 0.36666301  1.3355073\n  nearDistance 439.92169\n  farDistance 2327.0491\n  aspectRatio 1\n  focalDistance 1382.543\n  height 2765.0859\n\n}\n')
#
#  ----
#
Gui.ActiveDocument.getObject("lp_footer_001").ShapeColor=(102/255, 14/255, 20/255)
Gui.ActiveDocument.getObject("ch_standard").ShapeColor=(0.8818247318267822, 0.4056229293346405, 0.4606013298034668, 0.0) #(0.0014737504534423351, 0.5847077369689941, 0.919508695602417, 0.5)
Gui.ActiveDocument.getObject("pd_support").ShapeColor= (51/255, 26/255, 7/255)
Gui.ActiveDocument.getObject("lp_notch_for_spacer").ShapeColor=(240/255, 230/255, 140/255)
Gui.ActiveDocument.getObject("lp_notch_for_spacer_002").ShapeColor=(0.6270631551742554, 0.3856086730957031, 0.053490329533815384, 0.0)
#Gui.ActiveDocument.getObject("ch_spacer_000").ShapeColor=(0.098, 0.859, 0.631)

this_wall_assembly = App.activeDocument().addObject('App::Part','Wall_assembly')
this_support_assembly = App.activeDocument().addObject('App::Part','Support_assembly')
this_shelf_assembly = App.activeDocument().addObject('App::Part','Shelf_assembly')

this_total_assembly = App.activeDocument().addObject('App::Part','Total_assembly')
this_total_assembly.setExpression('Placement.Base.y', u'2*(sp_footer.length+sp_joist.width)')
this_total_assembly.Group += [
    App.activeDocument().Wall_assembly, \
    App.activeDocument().Shelf_assembly, \
    App.activeDocument().Support_assembly, \
    ]
