#BEGIN Handmade file $HOME/Documents/FreeCAD/Busybox/busybox_006_handmade_standard_extension.FCMacro
FreeCAD.Console.PrintMessage("busybox_006_handmade_standard starts.") 

FreeCAD.Console.PrintMessage("busybox_006_handmade_standard_extension starts standard001.\n") 

#features_ = [App.ActiveDocument.sk_standard]
#App.ActiveDocument.Footer.removeObjects(features_)
this_sketch = App.ActiveDocument.sk_standard001
this_body = App.ActiveDocument.bd_standard
this_pad_extension = this_body.newObject("PartDesign::Pad","pd_standard_extension001")
this_pad_extension.Profile = this_sketch
this_pad_extension.Length = 10.0
this_pad_extension.setExpression('Length', u'sp_global.elevation - sp_joist.height')
FreeCAD.Console.PrintMessage("busybox_006_handmade_standard after line 16.\n") 
this_pad_extension.Length2 = 99.999800
this_pad_extension.Type = 0
this_pad_extension.UpToFace = None
this_pad_extension.Reversed = 0
this_pad_extension.Midplane = 0
this_pad_extension.Offset = 0.000000
FreeCAD.Console.PrintMessage("busybox_006_handmade_standard_extension is midway.\n") 
#
#  ----
#
this_sketch = App.ActiveDocument.sk_standard001
this_body = App.ActiveDocument.bd_standard
this_pad_extension = this_body.newObject("PartDesign::Pad","pd_standard001")
this_pad_extension.Profile = this_sketch
this_pad_extension.Length = 10.0
this_pad_extension.setExpression('Length', u'sp_standard.height')
FreeCAD.Console.PrintMessage("busybox_006_handmade_standard after line 32.\n") 
this_pad_extension.Length2 = 99.999800
this_pad_extension.Type = 0
this_pad_extension.UpToFace = None
this_pad_extension.Reversed = 1
this_pad_extension.Midplane = 0
this_pad_extension.Offset = 0.000000

Gui.activeDocument().hide("pd_joist_loadcell002")
Gui.activeDocument().hide("pd_standard_extension001")

FreeCAD.Console.PrintMessage("busybox_006_handmade_standard_extension is finished.\n") 

#END Handmade file $HOME/Documents/FreeCAD/Busybox/busybox_006_handmade_standard_extension.FCMacro
