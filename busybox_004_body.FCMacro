# -*- coding: utf-8 -*-

# Macro Begin: /home/amcintosh/.FreeCAD/Macro/shelves_007_standard_body.FCMacro +++++++++++++++++++++++++++++++++++++++++++++++++
import FreeCAD
import PartDesign

# --------------------------------------------------------
# --  Set the level of this shelf in the Python console.
# --    e.g. level = 0
level = int(App.ActiveDocument.sp_global.get(App.ActiveDocument.sp_global.getCellFromAlias("level")))
FreeCAD.Console.PrintMessage("Starting busybox_004_body with level " + str(level) + "\n")
# --------------------------------------------------------
# --- This is very handy ---> Gui.Selection.getSelectionEx()[0].SubElementNames
facelist = [16, 69, 105, 141, 177, 213]

if 0==level:
 group_bodies = App.ActiveDocument.addObject('App::DocumentObjectGroup', 'group_bodies_' + str(1+level))
 this_body = group_bodies.newObject("PartDesign::Body","bd_standard_" + str(1+level))
else:
 group_bodies = App.ActiveDocument.group_bodies_1
 this_body = App.ActiveDocument.bd_standard_1

#This for loop is the only place where sketches are copied.
for i in App.ActiveDocument.group_sketches.Group:
 aux_sketch = App.ActiveDocument.copyObject(i) #American numbering scheme:  from "1", then "0" is reference
 #FreeCAD.Console.PrintMessage("The new sketch name is: " + aux_sketch.Name + " (" + aux_sketch.Label + ")\n")
 #FreeCAD.Console.PrintMessage(" The placement is: " + aux_sketch.Placement.Base.__str__() + "\n")
 this_body.Group += [aux_sketch ,]
 i.Placement.Base.z = (level+1) * 15 * 25.4  #sketch_000 carries the .z value for the next iteration.
 Gui.activeDocument().hide(aux_sketch.Name)


#
# --- 
#
App.ActiveDocument.recompute()
this_support = this_body.newObject("PartDesign::Pad","pd_support_00" + str(1+level))
this_support.Profile = App.ActiveDocument.getObject("sk_support_00" + str(1+level))
this_support.Length = 10.0
this_support.setExpression('Length', u'sp_support.length')
this_support.Length2 = 99.999800
this_support.Type = 0
this_support.UpToFace = None
this_support.Reversed = 1
this_support.Midplane = 0
this_support.Offset = 0.000000
Gui.activeDocument().hide(this_support.Name)
#
# ----
#
this_pad = this_body.newObject("PartDesign::Pad","pd_standardF_00" + str(1+level))
this_pad.Profile = App.ActiveDocument.getObject("sk_standardF_00" + str(1+level))
this_pad.Length = 10.0
this_pad.setExpression('Length', u'sp_standard.height')
this_pad.Length2 = 99.999800
this_pad.Type = 0
this_pad.UpToFace = None
this_pad.Reversed = 0
this_pad.Midplane = 0
this_pad.Offset = 0.000000
Gui.activeDocument().hide(this_pad.Name)
#
# ----
#
this_pad = this_body.newObject("PartDesign::Pad","pd_standardB_00" + str(1+level))
this_pad.Profile = App.ActiveDocument.getObject("sk_standardB_00" + str(1+level))
this_pad.Length = 10.0
this_pad.setExpression('Length', u'sp_standard.height')
this_pad.Length2 = 99.999800
this_pad.Type = 0
this_pad.UpToFace = None
this_pad.Reversed = 1
this_pad.Midplane = 0
this_pad.Offset = 0.000000
Gui.activeDocument().hide(this_pad.Name)
#
# ----
#
this_pad = this_body.newObject("PartDesign::Pad","pd_joist_00" + str(1+level))
this_sketch = App.ActiveDocument.getObject("sk_joist_00" + str(1+level))
this_pad.Profile = this_sketch
this_pad.Length = 10.0
this_pad.setExpression('Length', u'sp_joist.length')
this_pad.Length2 = 99.999800
this_pad.Type = 0
this_pad.UpToFace = None
this_pad.Reversed = 0
this_pad.Midplane = 0
this_pad.Offset = 0.000000
Gui.activeDocument().hide(this_sketch.Name)
Gui.activeDocument().hide(this_pad.Name)
#
this_pad_extension = this_body.newObject("PartDesign::Pad","pd_joist_extend_00" + str(1+level))
this_pad_extension.Profile = App.ActiveDocument.getObject("sk_joist_00" + str(1+level))
this_pad_extension.Length = 10.0
this_pad_extension.setExpression('Length', u'sp_standard.length')
this_pad_extension.Length2 = 99.999800
this_pad_extension.Type = 0
this_pad_extension.UpToFace = None
this_pad_extension.Reversed = 1
this_pad_extension.Midplane = 0
this_pad_extension.Offset = 0.000000
Gui.activeDocument().hide(this_sketch.Name)
Gui.activeDocument().hide(this_pad_extension.Name)
#
# ----
#
this_loadcell = this_body.newObject("PartDesign::Pad","pd_joist_loadcell_00" + str(1+level))
this_loadcell.Profile = (this_pad_extension, ["Face" + str(facelist[level])])
this_loadcell.setExpression('Length', u'sp_standard.length/2')
this_loadcell.Reversed = 0
this_loadcell.Length2 = 99.999800
this_loadcell.Type = 0
this_loadcell.UpToFace = None
this_loadcell.Midplane = 0
this_loadcell.Offset = 0.000000
#App.activeDocument().bd_standard.Group = [App.activeDocument().sk_standardF, ]
#
# ----
#
Gui.activeDocument().show(this_loadcell.Name)
#
# ----
#
App.ActiveDocument.recompute()
Gui.activeDocument().activeView().viewIsometric()
Gui.SendMsgToActiveView("ViewFit")

# Macro End: /home/amcintosh/.FreeCAD/Macro/shelves_008_standard_body_addendum.FCMacro +++++++++++++++++++++++++++++++++++++++++++++++++

App.ActiveDocument.sp_global.set(App.ActiveDocument.sp_global.getCellFromAlias("level"), str(level+1))

# hints
#App.ActiveDocument.getObject("sk_support_002")
