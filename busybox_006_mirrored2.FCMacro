# -*- coding: utf-8 -*-

# Macro Begin: /home/amcintosh/Documents/FreeCAD/Busybox/busybox_006_mirrored2.FCMacro +++++++++++++++++++++++++++++++++++++++++++++++++
import FreeCAD
import PartDesign

this_mirror = App.activeDocument().bd_standard.newObject("PartDesign::Mirrored","Mirrored002")
App.ActiveDocument.recompute()
this_mirror.Originals = [App.activeDocument().pd_joist_loadcell,]
this_mirror.MirrorPlane = (App.activeDocument().XY_Plane, [""])
App.activeDocument().bd_standard.Tip = this_mirror
Gui.activeDocument().show("Mirrored002")
App.ActiveDocument.Mirrored002.MirrorPlane = (App.ActiveDocument.Mirrored001, ["Face42"])
this_mirror.Originals = [App.ActiveDocument.pd_joist_loadcell, App.ActiveDocument.pd_joist, \
    App.ActiveDocument.pd_joist_extend,App.ActiveDocument.pd_support, App.ActiveDocument.pd_standard_extend, \
    App.ActiveDocument.pd_standard, ]
Gui.activeDocument().hide("Mirrored001")
#
# ----
#
#this_plane = App.activeDocument().bd_standard.newObject('PartDesign::Plane','DatumPlane_procedural')

#this_vec = App.Vector(1, -1, 0)
#this_vec.Length = 1
#this_rot = App.Rotation(this_vec, 90)
#this_plane.Placement.Rotation = this_rot

#this_plane.setExpression('Placement.Base.x', u'sp_joist.length')
#this_plane.setExpression('Placement.Base.y', u'sp_support.length + sp_standard.length/2')
Gui.getDocument("BusyBox_ver_1_0").getObject("Mirrored002").ShapeColor=(0.72,0.97,0.16)

# Macro End: /home/amcintosh/Documents/FreeCAD/Busybox/busybox_006_mirrored2.FCMacro +++++++++++++++++++++++++++++++++++++++++++++++++
